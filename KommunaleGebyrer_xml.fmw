FME workspace KommunaleGebyrer_xml.fmw

Parameters:
- Ordrenavn =
- GNR =
- BNR =
- FNR =
- SNR =
- ref =   # Referanse
- DestDataset_TEXTLINE = $(FME_MF_DIR_USERTYPED)ftp\upload\xml\resultset_2473_$(Ordrenavn).xml.xml   # Destination Text File
- SourceDataset_XLSXR = $(FME_MF_DIR)KommunaleGebyrer2017.xlsx   # Source Microsoft Excel File(s)
- SourceDataset_MSSQL_ADO = ENE_U_FAKTURERING   # SQL Server Connection

Readers:
- MSSQL_ADO_1: MSSQL_ADO from $(SourceDataset_MSSQL_ADO)
- XLSXR_1: XLSXR from $(SourceDataset_XLSXR)

Writers:
- TEXTLINE_1: TEXTLINE to $(DestDataset_TEXTLINE)

Bookmark: Tabell
dbo.U_AVGGRUNL (reader MSSQL_ADO_1)
    attributes: U_SELSKAP smallint, U_REGION integer, U_BNR smallint, U_BYGNNR smallint, U_FESTENR smallint, U_FRADATO integer, U_FRITILL varchar(2), U_GJELDTIL integer, U_GNR integer, U_GRUNNLAG numeric(15,2), U_OPPDRGNR smallint, U_TILDATO integer, U_UFESTENR smallint, U_VARENR smallint, U_PROSENT numeric(7,2), U_LOPENR smallint, U_AGVAREGR varchar(16), U_BELOP numeric(15,2), U_KSID integer, U_MVAKODE smallint, U_GJELDFRA integer
    -> AttributeKeeper_2
AttributeKeeper_2
    KEEP_ATTRS = U_FESTENR,U_GNR,U_GRUNNLAG,U_UFESTENR,U_OPPDRGNR,U_BNR,U_VARENR
    -> FeatureMerger_2 [REQUESTOR]
Ark1 (reader XLSXR_1)
    attributes: Varenavn char(119), Oppdragsgiver number(3,0), Varenr. number(4,0), Ekskl. mva number(10,5), Inkl.mva number(13,7), Fakturering  char(16), Merknad char(117), H string
    -> FeatureMerger_2 [SUPPLIER]
FeatureMerger_2
    PROCESS_DUPS = No
    ATTR_ACCUM_MODE = Merge Supplier
    SUPPLIERS_FIRST = No
    ATTR_CONFLICT_RES = Use Requestor
    IGNORE_NULLS = No
    JOIN_KEYS = @Value(U_VARENR) @Value(Varenr.) AUTO
    REJECT_NULL_MISSING_KEYS = No
    MERGE_TYPE = Attributes Only
    MERGED -> ParameterFetcher
ParameterFetcher
    ATTR_LIST = _Ordrenavn {$(Ordrenavn)} _ref {$(ref)}
    -> AttributeSplitter
AttributeSplitter
    LIST_NAME = _onvn
    DROP_EMPTY_PARTS = No
    DELIMITER = .
    ATTR_NAME = _Ordrenavn
    TRIM_OPTION = Both
    -> AttributeHandler
AttributeHandler
    INKL.MVA = @Value(Inkl.mva)
    U_UFESTENR = @Value(U_UFESTENR)
    U_GRUNNLAG = @Value(U_GRUNNLAG)
    FAKTURERING_ = @Value(Fakturering )
    VARENAVN = @Value(Varenavn)
    VARENR. = @Value(Varenr.)
    U_FESTENR = @Value(U_FESTENR)
    U_VARENR = @Value(U_VARENR)
    EKSKL._MVA = @Value(Ekskl. mva)
    U_GNR = @Value(U_GNR)
    _REF = @Value(_ref)
    MERKNAD = @Value(Merknad)
    U_BNR = @Value(U_BNR)
    -> XMLTemplater [ROOT]
XMLTemplater
    OUTPUT_XML_HEADER = No
    VISIBLE_QUERY_VALIDATE = No
    ROOT_QUERY_FILE = $(FME_MF_DIR)XML\kommunale_avgifter_template.xml
    RESULT_ATTRIBUTE = text_line_data
    -> XMLFormatter
Note: Pretty-print and check validity
XMLFormatter
    REMOVE_ALL_COMMENT = No
    COLLAPSE_EMPTY_ELEMENT = No
    OUTPUT_ENCODING = iso-8859-1
    XML_ATTR_TEXT = text_line_data
    FORMATTING_CHOICE = Pretty-Print XML
    INDENT_SIZE = 1
    TEXT_INDENT = no
    SCHEMALOC_CLEANUP = No
    REMOVE_EMPTY_ELEMENT = No
    NAMESPACE_CLEANUP = No
    LIST_NAME = _xml_error
    XML_INPUT_TYPE = Attribute Specifying XML Text
    XML_OUTPUT_ATTR = text_line_data
    XML_OUTPUT_TYPE = Attribute
    REPLACE_TABS_WITH_SPACES = no
    WHITESPACE_HANDLING = Preserve all whitespace
    PASSED -> text_line (writer TEXTLINE_1)
text_line (writer TEXTLINE_1)
    attributes: text_line_data buffer

FME custom transformer AttributeHandler

Parameters:
- INKL.MVA = @Value(Inkl.mva)   # Inkl.mva
- U_VARENR = @Value(U_VARENR)   # U Varenr
- EKSKL._MVA = @Value(Ekskl. mva)   # Ekskl. mva
- FAKTURERING_ = @Value(Fakturering )   # Fakturering 
- MERKNAD = @Value(Merknad)   # Merknad
- U_GRUNNLAG = @Value(U_GRUNNLAG)   # U Grunnlag
- VARENAVN = @Value(Varenavn)   # Varenavn
- VARENR. = @Value(Varenr.)   # Varenr.
- U_BNR = @Value(U_BNR)   # U Bnr
- U_FESTENR = @Value(U_FESTENR)   # U Festenr
- U_GNR = @Value(U_GNR)   # U Gnr
- U_UFESTENR = @Value(U_UFESTENR)   # U Ufestenr
- _REF = @Value(_ref)   # Ref

Input (input)
    -> AttributeManager
AttributeManager
    ATTR_TABLE:
      RENAME_SET_VALUE U_BNR > BNR
      RENAME_SET_VALUE U_FESTENR > FNR
      RENAME_SET_VALUE U_GNR > GNR
      RENAME_SET_VALUE U_UFESTENR > SNR
      SET_TO KOMM = 0229
      SET_TO ADRESSE = ""
      SET_TO Ordrenr = @Value(_onvn{0})
      SET_TO Ordretype = @Value(_onvn{1})
      SET_TO J_N_Vannmaler = N
      SET_TO Kommentar = ""
      RENAME_SET_VALUE _ref > Referanse
      REMOVE _onvn{}
    -> TestFilter
TestFilter
    DEFAULT_VALUE = <UNFILTERED>
    TEST_LIST = BOOL_OP,OR,COMPOSITE_TEST,<Unused>,TEST_CLAUSE,"TEST @Value(U_VARENR) BEGINS_WITH 2",avløp,BOOL_OP,OR,COMPOSITE_TEST,<Unused>,TEST_CLAUSE,"TEST @Value(U_VARENR) BEGINS_WITH 3",renovasjon,BOOL_OP,OR,COMPOSITE_TEST,<Unused>,TEST_CLAUSE,"TEST @Value(U_VARENR) BEGINS_WITH 4",pipe,BOOL_OP,OR,COMPOSITE_TEST,<Unused>,TEST_CLAUSE,"TEST @Value(U_VARENR) BEGINS_WITH 5",slam
    avløp -> Aggregator_2
    renovasjon -> AttributeCreator_2
    pipe -> AttributeCreator_3
    slam -> AttributeCreator_4
Aggregator_2
    SEP = ,
    MODE = Geometry - Assemble One Level
    CONCAT_ATTRS = Inkl.mva Merknad U_GRUNNLAG
    ACCUM_ATTRS_NAME = Get Attributes From One Representative Feature
    ORDERED = No
    AGGREGATE_TYPE = Homogeneous Collection (If Possible)
    AGGREGATE -> AttributeCreator
AttributeCreator
    ATTR_TABLE:
      SET_TO avlop_grunnlag = @Value(U_GRUNNLAG)
      SET_TO avlop_kommentar = @Value(Merknad)
      SET_TO avlop_avgift = @Value(Inkl.mva)
      SET_TO id = 1
    -> FeatureMerger [REQUESTOR]
AttributeCreator_2
    ATTR_TABLE:
      SET_TO renovasjon_grunnlag = @Value(U_GRUNNLAG)
      SET_TO renovasjon_kommentar = @Value(Merknad)
      SET_TO renovasjon_avgift = @Value(Inkl.mva)
      SET_TO id = 1
    -> FeatureMerger [SUPPLIER]
AttributeCreator_3
    ATTR_TABLE:
      SET_TO pipe_grunnlag = @Value(U_GRUNNLAG)
      SET_TO pipe_kommentar = @Value(Merknad)
      SET_TO pipe_avgift = @Value(Inkl.mva)
      SET_TO id = 1
    -> FeatureMerger [SUPPLIER]
AttributeCreator_4
    ATTR_TABLE:
      SET_TO spredt_avlop_grunnlag = @Value(U_GRUNNLAG)
      SET_TO spredt_avlop_kommentar = @Value(Merknad)
      SET_TO spredt_avlop_avgift = @Value(Inkl.mva)
      SET_TO id = 1
    -> FeatureMerger [SUPPLIER]
FeatureMerger
    PROCESS_DUPS = Yes
    ATTR_ACCUM_MODE = Merge Supplier
    GEOM_TYPE = Build Aggregates
    SUPPLIERS_FIRST = No
    ATTR_CONFLICT_RES = Use Requestor
    IGNORE_NULLS = No
    JOIN_KEYS = @Value(id) @Value(id) AUTO
    REJECT_NULL_MISSING_KEYS = No
    MERGE_TYPE = Attributes Only
    MERGED -> Output (output)
    NOT_MERGED -> Output (output)
Output (output)
StatisticsCalculator
    SUM_ATTR = _sum
    STATS_ATTRS = Inkl.mva
    PREPEND_ATTR_NAME_CHOICE = For multiple results only
    COMPUTE_HISTOGRAM = NO
    COMPLETE -> Aggregator
Aggregator
    SEP = ,
    MODE = Geometry - Assemble One Level
    CONCAT_ATTRS = Merknad
    ACCUM_ATTRS_NAME = Get Attributes From One Representative Feature
    ORDERED = No
    AGGREGATE_TYPE = Homogeneous Collection (If Possible)
