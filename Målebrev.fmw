FME workspace Målebrev.fmw

Parameters:
- SourceDataset_PATH = X:\Data\Webdokumenter\Maalebrev\0229   # Source Folder and File Pathnames Folder
- gnr = 115   # Gårdsnr
- bnr = 1   # Bruksnr
- DestDataset_FILECOPY = $(FME_MF_DIR)ftp\upload   # Destination File Copy Folder
- Filname = målebrev.pdf   # Filename

Readers:
- PATH_1: PATH from $(SourceDataset_PATH)

Writers:
- FILECOPY_1: FILECOPY to $(DestDataset_FILECOPY)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> filecopy (writer FILECOPY_1)
filecopy (writer FILECOPY_1)
    attributes: filecopy_source_dataset char(512), filecopy_dest_dataset char(512), filecopy_dest_filename char(128)
