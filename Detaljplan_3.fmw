FME workspace Detaljplan_3.fmw

Parameters:
- filename = ts   # Navn
- DestDataset_PDF2D = $(FME_MF_DIR_USERTYPED)test\g3.pdf   # Destination PDF File
- _gnr = 115   # Gnr
- _bnr = 232   # Bnr
- _fnr = 0   # Fnr
- _snr = 0   # Snr
- A4 = YES   # A4 proportion
- DestDataset_SQLITE3 = X:\Data\SQLITE\0229_UTVALG_EIENDOM.sl3   # Destination SQLite Database File

Writers:
- PDF2D_1: PDF2D to $(DestDataset_PDF2D)

Creator
    NUM = 1
    GEOMTYPE = Geometry Object
    CREATED -> ParameterFetcher
ParameterFetcher
    ATTR_LIST = GNR {$(_gnr)} BNR {$(_bnr)} FNR {$(_fnr)} SNR {$(_snr)}
    -> WorkspaceRunner
WorkspaceRunner
    BLOCKING = Yes
    WORKSPACE_FILE = $(FME_MF_DIR)UTVALG_EIENDOM.fmw
    WORKSPACE_PARAMETERS = GNR,$(_gnr),BNR,$(_bnr),FNR,$(_fnr),SNR,$(_snr),DestDataset_SQLITE3,$(DestDataset_SQLITE3)
    SUCCEEDED -> FeatureReader [INITIATOR]
FeatureReader
    FEATURETYPES = Teig
    SPATIALITE_QUERY_FEATURE_TYPES_FOR_MERGE_FILTERS = Yes
    INTERACT = <No Spatial Filter>
    FORMAT = SPATIALITE
    DATASET = $(DestDataset_SQLITE3)
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    OUTPUT_FEATURES_DISPLAY = Schema and Data Features
    ATTR_ACCUM_MODE = Only Use Result
    COMBINE_GEOM = Use Result
    Teig -> BoundingBoxReplacer_2
    Teig -> MerkEiendom
MerkEiendom
    _snr = $(_snr)
    _gnr = $(_gnr)
    _bnr = $(_bnr)
    _fnr = $(_fnr)
    label -> MapnikRasterizer [Label00]
    Line -> MapnikRasterizer [Teig]
    Polygon -> MapnikRasterizer [Teig00]
BoundingBoxReplacer_2
    BOXTYPE = Bounding Box
    BOX -> Tester
Tester
    BOOL_OP = OR
    TEST_CLAUSE = TEST @Area() < 50000
    TEST_DESCRIPTION = ""
    TEST_MODE = Automatic
    PASSED -> WMS_3
    FAILED -> Terminator
WMS_3
    ratio_l = 271.75
    WMS_layer = GATENAVN,EIENDOMSKART,VEG_STREK,VANN_STREK,0229_RP3VN2
    WMS_url = http://195.1.20.83/wms-follo
    ratio_s = 210.0
    A4 = YES
    -> Ramme [BoundingBoxAccumulator_Input]
    -> MeasureLineCreator
    -> Bounding
    -> MapnikRasterizer [Output]
    -> TextRepalcer
Note: TextRepalcer [TextRepalcer] / [Embedded] / BNR: @Value(BNR) / FNR: @Value(FNR) / GNR: @Value(GNR) / SNR: @Value(SNR)
TextRepalcer
    FNR = @Value(FNR)
    GNR = @Value(GNR)
    SNR = @Value(SNR)
    BNR = @Value(BNR)
    Output_2 -> MapnikRasterizer [Output_2]
    Dato -> MapnikRasterizer [Output_3]
MeasureLineCreator
    Line -> MapnikRasterizer [Line]
    Label -> MapnikRasterizer [Label]
Bounding
    Higth = 24
    -> MapnikRasterizer [Top_layout]
    -> Ramme [BoundingBoxAccumulator_Input]
Ramme
    BoundsExtractor_Output -> MapnikRasterizer [Coerced]
    BoundsExtractor_Output -> BoundingBoxReplacer
MapnikRasterizer
    BACKGROUND_COLOR_ALPHA = 1.0
    COLROW_OR_SPACING = Spacing
    MAPNIK_CONFIG = Top_layout;raster;__ignore__raster-properties-group;;opacity;1;scaling;near;__ignore__comp-group;;comp-op;src-over;Output;raster;__ignore__raster-properties-group;;opacity;1;scaling;near;__ignore__comp-group;;comp-op;src-over;Output_2;text;__ignore__text-properties-group;;name;gnavn;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Output_3;text;__ignore__text-properties-group;;name;_timestamp;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Coerced;line;__ignore__color-group;;stroke;0,0,0;stroke-opacity;1;__ignore__line-style-group;;stroke-width;9;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Line;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over;Teig00;polygon;__ignore__color-group;;fill;1,0.607843,0.607843;fill-opacity;0.3;__ignore__smoothing-group;FME_DISCLOSURE_OPEN;gamma;1;gamma-method;linear;smooth;0;__ignore__comp-group;FME_DISCLOSURE_OPEN;comp-op;src-over;Teig;line;__ignore__color-group;;stroke;1,0,0;stroke-opacity;1;__ignore__line-style-group;;stroke-width;3;stroke-linejoin;miter;stroke-linecap;butt;stroke-dasharray;"12 6";stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Label00;text;__ignore__text-properties-group;;name;salgsobjekt;face-name;Tahoma,Normal;size;10;__ignore__color-group;;fill;1,0,0;opacity;1;halo-fill;1,1,1;halo-radius;0;__ignore__positioning-group;;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;;comp-op;src-over;Label;text;__ignore__text-properties-group;;name;label;face-name;Tahoma,Normal;size;@Evaluate(4*@Value(dy));__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;middle;justify-alignment;center;vertical-alignment;top;__ignore__comp-group;;comp-op;src-over
    INTERPRETATION_TYPE = RGBA32
    LAYER_CARDINALITY = Each rendering rule is a layer
    GROUND_EXTENTS_MIN_X = @Value(xmin)
    BACKGROUND_COLOR = 1,1,1
    GROUND_EXTENTS_MAX_X = @Value(ymin)
    GROUND_EXTENTS_MIN_Y = @Value(xmax)
    GROUND_EXTENTS_MAX_Y = @Value(ymax)
    SPACING = 0.1
    SPECIFY_GROUND_EXTENTS = Specify ground extents
    RASTER -> Clipper [CLIPPEE]
BoundingBoxReplacer
    BOXTYPE = Bounding Box
    BOX -> Clipper [CLIPPER]
Clipper
    PRESERVE_CLIPPEE_EXTENTS = No
    CREATE_AGGREGATES = Yes
    CONNECT_Z_MODE = First Wins
    BOUNDARY_CASES = Treat as Inside
    CLIP_TYPE = Multiple Clippers
    CLIPPED_ATTR = _clipped
    LINES_AS_SEGMENTS = No
    INSIDE -> PDFPageFormatter [Inside]
PDFPageFormatter
    PAGE_ORIENTATION = Portrait
    PAGE_WIDTH_USER = 21
    PAGE_NUMBER = 1
    PAGE_UNITS = Centimeters
    PAGE_HEIGHT_PTS = 842
    PAGE_HEIGHT_USER = 29.7
    PAGE_SIZE = A4
    PAGE_WIDTH_PTS = 595
    PAGE_OBJECTS = "Inside WIDTH;566.93;FIXED_ASPECT;Yes;SIZE_PARAMS;;MINY;14.29;MINX;14.17;HEIGHT;813.54;CLIPPING_ENABLED;No;SCALING_PARAMS;"
    -> Teig (writer PDF2D_1)
Teig (writer PDF2D_1)
Terminator
    MESSAGE = Translation Terminated

FME custom transformer MeasureLineCreator

Input (input)
    -> BoundsExtractor
BoundsExtractor
    XMIN = _xmin
    YMIN = _ymin
    XMAX = _xmax
    YMAX = _ymax
    -> AttributeCreator
AttributeCreator
    ATTR_TABLE:
      SET_TO size = @ceil(@Evaluate(@Value(_xmax)-@Value(_xmin))/5)
      SET_TO dy = @floor(@Evaluate((@Value(_ymax)-@Value(_ymin))/15))
      SET_TO dx = @floor(@Evaluate((@Value(_ymax)-@Value(_ymin))/15))
    -> TestFilter
TestFilter
    TEST_LIST:
      BOOL_OP,AND,COMPOSITE_TEST,<Unused>,TEST_CLAUSE,"TEST @Value(size) >= 0
      TEST @Value(size) < 100",< 100,BOOL_OP,AND,COMPOSITE_TEST,<Unused>,TEST_CLAUSE,"TEST @Value(size) >= 100
      TEST @Value(size) < 1000",< 1000,BOOL_OP,AND,COMPOSITE_TEST,<Unused>,TEST_CLAUSE,"TEST @Value(size) >= 1000
      TEST @Value(size) < 10000",< 10000,BOOL_OP,AND,COMPOSITE_TEST,<Unused>,TEST_CLAUSE,"TEST @Value(size) >= 10000
      TEST @Value(size) < 100000",< 100000
    DEFAULT_VALUE = <UNFILTERED>
    < 100 -> AttributeRounder
    < 1000 -> AttributeRounder_2
    < 10000 -> AttributeRounder_3
    < 100000 -> AttributeRounder_4
AttributeRounder
    ROUND_TYPE = Nearest
    PLACES = -1
    SRC_ATTRS = size
    -> VertexCreator
AttributeRounder_2
    ROUND_TYPE = Nearest
    PLACES = -2
    SRC_ATTRS = size
    -> VertexCreator
VertexCreator
    YVAL = @Evaluate(@Value(_ymin)+@Value(dy))
    XVAL = @Evaluate(@Value(_xmax)-@Value(dx))
    MODE_NAME = Replace with Point
    -> VertexCreator_2
    -> VertexCreator_5
VertexCreator_5
    YVAL = @Evaluate(@Value(_ymin)+2*@Value(dy))
    XVAL = @Evaluate(@Value(_xmax)-@Value(dx))
    MODE_NAME = Add Point
    -> Line (output)
VertexCreator_2
    YVAL = @Evaluate(@Value(_ymin)+@Value(dy))
    XVAL = @Evaluate(@Value(_xmax)-@Value(dx)-@Value(size))
    MODE_NAME = Add Point
    -> AttributeCreator_2
    -> VertexCreator_6
VertexCreator_6
    YVAL = @Evaluate(@Value(_ymin)+2*@Value(dy))
    XVAL = @Evaluate(@Value(_xmax)-@Value(dx)-@Value(size))
    MODE_NAME = Add Point
    -> Line (output)
AttributeCreator_2
    ATTR_TABLE = SET_TO BENEVNING = m
    -> Line (output)
    -> AttributeCreator_4
Line (output)
AttributeRounder_3
    ROUND_TYPE = Nearest
    PLACES = -3
    SRC_ATTRS = size
    -> VertexCreator_3
AttributeRounder_4
    ROUND_TYPE = Nearest
    PLACES = -4
    SRC_ATTRS = size
    -> VertexCreator_3
VertexCreator_3
    YVAL = @Evaluate(@Value(_ymin)+@Value(dy))
    XVAL = @Evaluate(@Value(_xmax)-@Value(dx))
    MODE_NAME = Replace with Point
    -> VertexCreator_4
VertexCreator_4
    YVAL = @Evaluate(@Value(_ymin)+@Value(dy))
    XVAL = @Evaluate(@Value(_xmax)-@Value(dx)-@Value(size))
    MODE_NAME = Add Point
    -> AttributeCreator_3
AttributeCreator_3
    ATTR_TABLE:
      SET_TO BENEVNING = Km
      SET_TO size = @Evaluate(@Value(size)/1000)
    -> AttributeCreator_4
AttributeCreator_4
    ATTR_TABLE = SET_TO label = @int(@Value(size))@Value(BENEVNING)
    -> LabelPointReplacer
LabelPointReplacer
    LABATTR = @Value(label)
    HEIGHT = @Evaluate(2*@Value(dy))
    ALWAYSROTATE = yes
    LabelPoint -> Label (output)
Label (output)

FME custom transformer WMS_3

Parameters:
- WMS_url =
- WMS_layer =
- Username =   # Enter Username
- password =   # Enter password
- A4 = NO   # A4 proportion
- ratio_l = 229.75   # Length of long side
- ratio_s = 210.0   # Length of shorter side

Input (input)
    -> BoundsExtractor
BoundsExtractor
    XMIN = _hmin
    YMIN = _vmin
    XMAX = _hmax
    YMAX = _vmax
    -> Tester
Tester
    BOOL_OP = OR
    TEST_CLAUSE = TEST $(A4) = NO
    TEST_DESCRIPTION = ""
    TEST_MODE = Automatic
    PASSED -> AttributeCreator
    FAILED -> ParameterFetcher
ParameterFetcher
    ATTR_LIST = _ratio_l {$(ratio_l)} _ratio_s {$(ratio_s)}
    -> AttributeCreator_4
AttributeCreator_4
    ATTR_TABLE:
      SET_TO _ratio_l = @real64(@Value(_ratio_l))
      SET_TO _ratio_s = @real64(@Value(_ratio_s))
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self.hmax=feature.getAttribute('_hmax')
              self.hmin=feature.getAttribute('_hmin')
              self.vmax=feature.getAttribute('_vmax')
              self.vmin=feature.getAttribute('_vmin')

              self.dh=self.hmax-self.hmin
              self.dv=self.vmax-self.vmin

              self.hmean = (self.hmax + self.hmin)/2.0
              self.vmean = (self.vmax + self.vmin)/2.0

              if self.dv < feature.getAttribute('_ratio_l') and self.dh < feature.getAttribute('_ratio_s'):
                  self.vmin= self.vmean-feature.getAttribute('_ratio_l')/2.0
                  self.vmax= self.vmean+feature.getAttribute('_ratio_l')/2.0
                  self.hmin = self.hmean-feature.getAttribute('_ratio_s')/2.0
                  self.hmax = self.hmean+feature.getAttribute('_ratio_s')/2.0
              elif self.dh > self.dv and self.dv > feature.getAttribute('_ratio_l'):
                  self.ndv = self.dh*(feature.getAttribute('_ratio_l')/feature.getAttribute('_ratio_s'))
                  self.vmin= self.vmean-self.ndv/2.0
                  self.vmax= self.vmean+self.ndv/2.0
              elif self.dh < self.dv and self.dh > feature.getAttribute('_ratio_s'):
                  self.ndh  = self.dv*(feature.getAttribute('_ratio_s')/feature.getAttribute('_ratio_l'))
                  self.hmin = self.hmean-self.ndh/2.0
                  self.hmax = self.hmean+self.ndh/2.0
              else:
                  raise Exception('condition not met')
                  print 'condition not met'


              #self.dh=self.hmax-self.hmin
              #self.dv=self.vmax-self.vmin

              #print self.dh, self.dv

              feature.setAttribute('_hmax',self.hmax)
              feature.setAttribute('_hmin',self.hmin)
              feature.setAttribute('_vmax',self.vmax)
              feature.setAttribute('_vmin',self.vmin)
              self.pyoutput(feature)
          def close(self):
              pass
    -> VertexCreator
VertexCreator
    YVAL = @Value(_vmin)
    XVAL = @Value(_hmin)
    MODE_NAME = Replace with Point
    -> VertexCreator_2
VertexCreator_2
    YVAL = @Value(_vmax)
    XVAL = @Value(_hmax)
    MODE_NAME = Add Point
    -> BoundingBoxReplacer
BoundingBoxReplacer
    BOXTYPE = Bounding Box
    BOX -> AttributeCreator
AttributeCreator
    ATTR_TABLE:
      SET_TO h_t = @Evaluate(@round((@Value(_hmax)-@Value(_hmin))/200)+1)
      SET_TO v_t = @Evaluate(@round((@Value(_vmax)-@Value(_vmin))/200)+1)
      SET_TO dh = @Evaluate(@Value(_hmax)-@Value(_hmin))
      SET_TO dv = @Evaluate(@Value(_vmax)-@Value(_vmin))
    -> Tester_2
Tester_2
    BOOL_OP = OR
    TEST_CLAUSE:
      TEST @Value(dv) > 1000
      TEST @Value(dh) > 1000
    TEST_DESCRIPTION = ""
    TEST_MODE = Automatic
    PASSED -> Tiler
    FAILED -> AttributeRemover_3
Tiler
    TILING_TYPE = Tile Size
    COL_ATTR = _column
    XINC = 1000
    YINC = 1000
    BOUNDARY_CASES = No
    ROW_ATTR = _row
    TILED -> AttributeRemover
AttributeRemover
    REMOVE_ATTRS = _vmax,_vmin,_column,h_t,_hmax,_hmin,v_t,_row
    -> BoundsExtractor_2
BoundsExtractor_2
    XMIN = _xmin
    YMIN = _ymin
    XMAX = _xmax
    YMAX = _ymax
    -> AttributeRounder
AttributeRounder
    ROUND_TYPE = Up
    PLACES = 0
    SRC_ATTRS = _xmax _ymax
    -> AttributeRounder_2
AttributeRounder_2
    ROUND_TYPE = Down
    PLACES = 0
    SRC_ATTRS = _xmin _ymin
    -> AttributeCreator_2
AttributeCreator_2
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*3)&HEIGHT=@Evaluate((@Value(_ymax)-@Value(_ymin))*3)&SRS=EPSG:25832&TRANSPARENT=true&BBOX=@Value(_xmin),@Value(_ymin),@Value(_xmax),@Value(_ymax)&
    -> HTTPCaller_3
HTTPCaller_3
    TARGET_ATTR_ENCODING = auto-detect
    AUTH_PASSWORD = $(password)
    VERIFY_SSL_CERTIFICATES = Yes
    RESPONSE_HEADER_LIST_ATTR = _headers
    AUTH_USERNAME = $(Username)
    FOLLOW_REDIRECTS = Yes
    AUTH_METHOD = Basic
    CONNECTION_TIMEOUT_LENGTH = 60
    SAVE_FILE = Attribute
    STATUS_CODE_ATTR = _http_status_code
    TARGET_ATTR = _response_body
    HTTP_METHOD = GET
    USE_COOKIES = No
    TRANSFER_TIMEOUT_LENGTH = 90
    TARGET_URL = @Value(_wms2)
    ERROR_ATTR = _error
    -> RasterReplacer_2
AttributeRemover_3
    REMOVE_ATTRS = _hmin,_vmax,_vmin,dv,v_t,dh,_hmax,h_t
    -> BoundsExtractor_3
BoundsExtractor_3
    XMIN = _xmin
    YMIN = _ymin
    XMAX = _xmax
    YMAX = _ymax
    -> AttributeRounder_3
AttributeRounder_3
    ROUND_TYPE = Up
    PLACES = 0
    SRC_ATTRS = _xmax _ymax
    -> AttributeRounder_4
AttributeRounder_4
    ROUND_TYPE = Down
    PLACES = 0
    SRC_ATTRS = _xmin _ymin
    -> AttributeCreator_3
AttributeCreator_3
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*4)&HEIGHT=@Evaluate((@Value(_ymax)-@Value(_ymin))*4)&SRS=EPSG:25832&TRANSPARENT=true&BBOX=@Value(_xmin),@Value(_ymin),@Value(_xmax),@Value(_ymax)&
    -> HTTPCaller_2
HTTPCaller_2
    TARGET_ATTR_ENCODING = auto-detect
    AUTH_PASSWORD = $(password)
    VERIFY_SSL_CERTIFICATES = Yes
    RESPONSE_HEADER_LIST_ATTR = _headers
    AUTH_USERNAME = $(Username)
    FOLLOW_REDIRECTS = Yes
    AUTH_METHOD = Basic
    CONNECTION_TIMEOUT_LENGTH = 60
    SAVE_FILE = Attribute
    STATUS_CODE_ATTR = _http_status_code
    TARGET_ATTR = _response_body
    HTTP_METHOD = GET
    USE_COOKIES = No
    TRANSFER_TIMEOUT_LENGTH = 90
    TARGET_URL = @Value(_wms)
    ERROR_ATTR = _error
    -> RasterReplacer_2
RasterReplacer_2
    BLOB_ATTR = _response_body
    FORMAT = PNGRASTER
    REMOVE_ATTRIBUTE = No
    -> RasterCheckpointer
RasterCheckpointer
    -> RasterGeoreferencer_2
RasterGeoreferencer_2
    X_UR_COORD = @Value(_xmax)
    Y_UR_COORD = @Value(_ymax)
    X_LR_COORD = @Value(_xmax)
    X_LL_COORD = @Value(_xmin)
    Y_UL_COORD = @Value(_ymax)
    POINTANDANGLE_OR_EXTENTS = Extents
    Y_LL_COORD = @Value(_ymin)
    Y_LR_COORD = @Value(_ymin)
    X_UL_COORD = @Value(_xmin)
    -> AttributeRemover_2
AttributeRemover_2
    LIST_ATTRS = _headers{} _headers{}.name _headers{}.value
    REMOVE_ATTRS = _ymax,_xmax,_ymin,_wms,_wms2,dv,_http_status_code,_xmin,dh,_response_body
    -> RasterCheckpointer_2
RasterCheckpointer_2
    -> RasterMosaicker
RasterMosaicker
    ACCUM_ATTRS_NAME = Get Attributes From One Representative Feature
    SNAPPING_TYPE_NAME = Resample
    NODATA_OVERWRITE = No
    MERGE_PALETTES_NAME = Yes
    INTERPOLATION_TYPE_NAME = Nearest Neighbor
    COMPOSITE_USING_ALPHA_BAND_NAME = No
    -> Output (output)
Output (output)

FME custom transformer Bounding

Parameters:
- Higth =   # Hight Frame

Input (input)
    -> BoundsExtractor
BoundsExtractor
    XMIN = _xmin
    YMIN = _ymin
    XMAX = _xmax
    ZMIN = _zmin
    YMAX = _ymax
    ZMAX = _zmax
    -> ParameterFetcher
ParameterFetcher
    ATTR_LIST = _Higth {$(Higth)}
    -> PythonCaller
PythonCaller
    PYTHONSYMBOL = FeatureProcessor
    PYTHONSOURCE:
      import fme
      import fmeobjects
      # Template Function interface:
      def processFeature(feature):
          pass

      # Template Class Interface:
      class FeatureProcessor(object):
          def __init__(self):
              self.y0=0
              self.y1=0
          def input(self,feature):
              self.y0 = float(feature.getAttribute('_ymax'))
              self.y  = float(feature.getAttribute('_ymin'))
              self.dy=self.y0 - self.y

              self.y1=self.y0+float(feature.getAttribute('_Higth'))*self.dy/252.0

              feature.setAttribute('_ymin',self.y0)
              feature.setAttribute('_ymax',self.y1)
              self.pyoutput(feature)
          def close(self):
              del self
    NEW_ATTRIBUTES = _ymin _ymax
    -> VertexCreator
VertexCreator
    YVAL = @Value(_ymin)
    XVAL = @Value(_xmin)
    MODE_NAME = Replace with Point
    -> VertexCreator_4
VertexCreator_4
    YVAL = @Value(_ymax)
    XVAL = @Value(_xmax)
    MODE_NAME = Add Point
    -> BoundsExtractor_2
BoundsExtractor_2
    XMIN = _xmin
    YMIN = _ymin
    XMAX = _xmax
    ZMIN = _zmin
    YMAX = _ymax
    ZMAX = _zmax
    -> FeatureReader [INITIATOR]
FeatureReader
    JPEG_APPLY_GCPS = No
    INTERACT = <No Spatial Filter>
    JPEG_USE_SEARCH_ENVELOPE = NO
    JPEG_GROUP_BY_DATASET = No
    FORMAT = JPEG
    DATASET = $(FME_MF_DIR_ENCODED)Layout\Meglerkart-Detaljplan.JPG
    ATTRIBUTES = JPEG,exif_artist
    JPEG_CLIP_TO_ENVELOPE = NO
    OUTPUT_FEATURES_DISPLAY = Schema and Data Features
    ATTR_ACCUM_MODE = Only Use Result
    COMBINE_GEOM = Use Result
    JPEG -> Counter_2
    INITIATOR -> Counter
Counter_2
    SCOPE = Local
    DOMAIN = id
    CNT_ATTR = id
    START = 0
    -> FeatureMerger [REQUESTOR]
Counter
    SCOPE = Local
    DOMAIN = id
    CNT_ATTR = id
    START = 0
    -> FeatureMerger [SUPPLIER]
FeatureMerger
    MERGE_TYPE = Attributes Only
    REJECT_NULL_MISSING_KEYS = No
    ATTR_ACCUM_MODE = Merge Supplier
    IGNORE_NULLS = No
    JOIN_KEYS = @Value(id) @Value(id) AUTO
    SUPPLIERS_FIRST = No
    PROCESS_DUPS = No
    ATTR_CONFLICT_RES = Use Requestor
    MERGED -> RasterGeoreferencer
RasterGeoreferencer
    X_UR_COORD = @Value(_xmax)
    Y_UR_COORD = @Value(_ymax)
    X_LR_COORD = @Value(_xmax)
    X_LL_COORD = @Value(_xmin)
    Y_UL_COORD = @Value(_ymax)
    POINTANDANGLE_OR_EXTENTS = Extents
    Y_LL_COORD = @Value(_ymin)
    Y_LR_COORD = @Value(_ymin)
    X_UL_COORD = @Value(_xmin)
    -> AttributeRemover
AttributeRemover
    REMOVE_ATTRS = _zmin,_ymin,_zmax,_xmax,pdf_page_number,_xmin,_ymax
    -> Output (output)
Output (output)

FME custom transformer TextRepalcer
Adds a number layer on each side.

Parameters:
- BNR = @Value(BNR)
- FNR = @Value(FNR)
- GNR = @Value(GNR)
- SNR = @Value(SNR)

Input (input)
    -> BoundingBoxReplacer
BoundingBoxReplacer
    BOXTYPE = Bounding Box
    BOX -> BoundsExtractor
BoundsExtractor
    XMIN = _xmin
    YMIN = _ymin
    XMAX = _xmax
    ZMIN = _zmin
    YMAX = _ymax
    ZMAX = _zmax
    -> PythonCaller_2
PythonCaller_2
    PYTHONSYMBOL = FeatureProcessor
    PYTHONSOURCE:
      import fme
      import fmeobjects
      # Template Function interface:
      def processFeature(feature):
          pass

      # Template Class Interface:
      class FeatureProcessor(object):
          def __init__(self):
              pass
          def input(self,feature):
              self.y0=feature.getAttribute('_ymax')
              self.y=feature.getAttribute('_ymin')

              self.y1=self.y0+9*(self.y0-self.y)/252
              self.y2=self.y0+3*(self.y0-self.y)/252
              self.hight=30*(self.y0-self.y)/252

              self.x=feature.getAttribute('_xmax')
              self.x0=feature.getAttribute('_xmin')

              self.x1=self.x0+39*(self.x-self.x0)/190
              self.x2=self.x0+39*(self.x-self.x0)/190 #tidligere + 97


              feature.setAttribute('_xmin',self.x1)
              feature.setAttribute('_ymax',self.y1)
              feature.setAttribute('_ymin',self.y2)
              feature.setAttribute('_xmax',self.x2)
              feature.setAttribute('text_hight',self.hight)

              self.pyoutput(feature)
          def close(self):
              del self
    NEW_ATTRIBUTES = _xmin _ymax _xmax _ymin text_hight
    -> VertexCreator_2
    -> VertexCreator_4
VertexCreator_2
    INDEX = 0
    YVAL = @Value(_ymax)
    XVAL = @Value(_xmin)
    MODE_NAME = Replace with Point
    -> StringFormatter
StringFormatter
    FORMAT = 4s
    SRC_ATTRS = GNR,BNR,SNR,FNR
    -> AttributeCreator
AttributeCreator
    ATTR_LIST = gnavn,GNR: @Value(GNR) BNR: @Value(BNR) FNR: @Value(FNR) SNR: @Value(SNR)
    -> LabelPointReplacer_2
LabelPointReplacer_2
    LABATTR = @Value(gnavn)
    HEIGHT = @Value(text_hight)
    ALWAYSROTATE = yes
    LabelPoint -> Output_2 (output)
Output_2 (output)
VertexCreator_4
    INDEX = 0
    YVAL = @Value(_ymin)
    XVAL = @Value(_xmax)
    MODE_NAME = Replace with Point
    -> TimeStamper
TimeStamper
    TIME_ATTR = _timestamp
    FMT = ^d.^m.^Y
    -> AttributeCreator_2
AttributeCreator_2
    ATTR_TABLE = SET_TO _timestamp = Dato: @Value(_timestamp)        Enebakk Kommune
    -> LabelPointReplacer_3
LabelPointReplacer_3
    LABATTR = @Value(_timestamp)
    HEIGHT = @Value(text_hight)
    ALWAYSROTATE = yes
    LabelPoint -> Dato (output)
Dato (output)

FME custom transformer Ramme

BoundingBoxAccumulator_Input (input)
    -> BoundingBoxAccumulator
BoundingBoxAccumulator
    ACCUM_ATTRS_NAME = Get Attributes From One Representative Feature
    TOPFER_INDEX = No
    BOUNDING_BOX -> GeometryCoercer
GeometryCoercer
    KIND = fme_line
    GQUERY:
      for $geom in //geometry
      where $geom/count(parent::geometry) = 0
      return number($geom/@fme_id)
    COERCED -> BoundsExtractor
BoundsExtractor
    XMIN = xmin
    YMIN = ymin
    XMAX = xmax
    YMAX = ymax
    -> BoundsExtractor_Output (output)
BoundsExtractor_Output (output)

FME custom transformer MerkEiendom

Parameters:
- _gnr = 115   # Gnr
- _bnr = 312   # Bnr
- _fnr = 0   # Fnr
- _snr = 0   # Snr

Input (input)
    -> DonutHoleExtractor
    -> Polygon (output)
DonutHoleExtractor
    OUTERSHELL -> GeometryCoercer
    HOLE -> GeometryCoercer
GeometryCoercer
    KIND = fme_line
    GQUERY:
      for $geom in //geometry
      where $geom/count(parent::geometry) = 0
      return number($geom/@fme_id)
    COERCED -> AttributeCreator
    COERCED -> Line (output)
AttributeCreator
    ATTR_TABLE = SET_TO salgsobjekt = Salgs objekt!
    -> Chopper
Chopper
    MODE = By Length
    GRID_AREAS = Yes
    CHOPPED_ATTR = _chopped
    APPROX_LENGTH = 50
    -> OrientationExtractor
OrientationExtractor
    ORIENTATION = _orientation
    -> LabelPointReplacer
LabelPointReplacer
    LABATTR = @Value(salgsobjekt)
    HEIGHT = 20
    ALWAYSROTATE = no
    LabelPoint -> label (output)
label (output)
Line (output)
Polygon (output)
