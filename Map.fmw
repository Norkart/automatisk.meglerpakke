FME workspace Map.fmw

Parameters:
- DestDataset_PDF2D = V:\FME\Ambitia\test\klokkerudåsen_1-2000.pdf   # Destination PDF File
- SCALE = 2000   # Select map scale
- GNR = 115
- BNR = 232
- FNR = 0
- SNR = 0
- ADRESSE = Klokkerudåsen 25N
- WMS_layer = ADRESSE,GNRBNR,AREALBRUK,PLAN_STREK,BANE,EIENDOMSKART,BYGNING,PBLTILTAK,BYGNANLEGG,GATENAVN,NATURINFO,TEKST,LEDNING,LEDNING_HOYSPENT,TRAKTORVEISTI,VEG,LEDNINGVA,TERRENG1,VANN   # WMS Lag
- layout_style = V:\FME\Ambitia\Layout\Meglerkart-Ledningsnett.JPG   # Choose Layout style
- Higth = 72   # Hight Frame
- TEXT_HIGHT_LAYOUT = 30   # Text Hight Layout
- X_DIST_LAYOUT = 39   # X Dist Layout
- Y_DIST_LAYOUT_TEXT_1 = 58   # Y Dist Layout Text 1
- Y_DIST_LAYOUT_TEXT_2 = 52   # Y Dist Layout Text 2

Writers:
- PDF2D_1: PDF2D to $(DestDataset_PDF2D)

Creator
    GEOMTYPE = Geometry Object
    NUM = 1
    CREATED -> ParameterFetcher
ParameterFetcher
    ATTR_LIST = _ADRESSE {$(ADRESSE)} BNR {$(BNR)} GNR {$(GNR)} FNR {$(FNR)} SNR {$(SNR)} _SCALE {$(SCALE)} _TEXT_HIGHT_LAYOUT {$(TEXT_HIGHT_LAYOUT)} _X_DIST_LAYOUT {$(X_DIST_LAYOUT)} _Y_DIST_LAYOUT_TEXT_1 {$(Y_DIST_LAYOUT_TEXT_1)} _Y_DIST_LAYOUT_TEXT_2 {$(Y_DIST_LAYOUT_TEXT_2)} _Higth {$(Higth)}
    -> CombinePolygonGenerators
CombinePolygonGenerators
    _ADRESSE = @Value(_ADRESSE)
    _SCALE = @Value(_SCALE)
    _CREATION_INSTANCE = @Value(_creation_instance)
    _HIGTH = @Value(_Higth)
    GNR = @Value(GNR)
    FNR = @Value(FNR)
    SNR = @Value(SNR)
    BNR = @Value(BNR)
    TeigGrenser -> MerkEiendom
    A4BoundingBox -> MeasureLineCreator
    A4BoundingBox -> TextRepalcer
    A4BoundingBox -> WMS_3
    A4BoundingBox -> CombineFrameAndLayout
    A4BoundingBox -> GridCreator
MerkEiendom
    _fnr = @Value(FNR)
    _snr = @Value(SNR)
    _bnr = @Value(BNR)
    _gnr = @Value(GNR)
    label -> MapnikRasterizer [Label00]
    Line -> MapnikRasterizer [Teig]
    Polygon -> MapnikRasterizer [Teig00]
WMS_3
    WMS_layer = $(WMS_layer)
    WMS_url = http://195.1.20.83/wms-follo
    -> MapnikRasterizer [Output]
TextRepalcer
    _Y_DIST_LAYOUT_TEXT_2 = @Value(_Y_DIST_LAYOUT_TEXT_2)
    _TEXT_HIGHT_LAYOUT = @Value(_TEXT_HIGHT_LAYOUT)
    _Y_DIST_LAYOUT_TEXT_1 = @Value(_Y_DIST_LAYOUT_TEXT_1)
    _SCALE = @Value(_SCALE)
    _HIGTH = @Value(_Higth)
    GNR = @Value(GNR)
    _X_DIST_LAYOUT = @Value(_X_DIST_LAYOUT)
    FNR = @Value(FNR)
    SNR = @Value(SNR)
    BNR = @Value(BNR)
    Output_2 -> MapnikRasterizer [Output_2]
    Dato -> MapnikRasterizer [Output_3]
MeasureLineCreator
    Line -> MapnikRasterizer [Line]
    Label -> MapnikRasterizer [Label]
CombineFrameAndLayout
    Higth = $(Higth)
    layout_style = $(layout_style)
    Frame -> MapnikRasterizer [Coerced]
    Frame -> BoundingBoxReplacer
    Layout -> MapnikRasterizer [Top_layout]
BoundingBoxReplacer
    BOXTYPE = Bounding Box
    BOX -> Clipper [CLIPPER]
GridCreator
    Line -> MapnikRasterizer [Line00]
    X -> MapnikRasterizer [X]
    Y -> MapnikRasterizer [Y]
MapnikRasterizer
    INTERPRETATION_TYPE = RGBA32
    LAYER_CARDINALITY = Each rendering rule is a layer
    BACKGROUND_COLOR = 1,1,1
    BACKGROUND_COLOR_ALPHA = 1.0
    COLROW_OR_SPACING = Spacing
    SPACING = 0.1
    SPECIFY_GROUND_EXTENTS = Use input data ground extents
    MAPNIK_CONFIG = Top_layout;raster;__ignore__raster-properties-group;;opacity;1;scaling;near;__ignore__comp-group;;comp-op;src-over;Output;raster;__ignore__raster-properties-group;;opacity;1;scaling;near;__ignore__comp-group;;comp-op;src-over;Output_2;text;__ignore__text-properties-group;;name;gnavn;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Output_3;text;__ignore__text-properties-group;;name;_timestamp;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Coerced;line;__ignore__color-group;;stroke;0,0,0;stroke-opacity;1;__ignore__line-style-group;;stroke-width;9;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Line;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over;Teig00;polygon;__ignore__color-group;;fill;1,0.607843,0.607843;fill-opacity;0.1;__ignore__smoothing-group;FME_DISCLOSURE_OPEN;gamma;1;gamma-method;linear;smooth;0;__ignore__comp-group;FME_DISCLOSURE_OPEN;comp-op;src-over;Teig;line;__ignore__color-group;;stroke;1,0,0;stroke-opacity;1;__ignore__line-style-group;;stroke-width;3;stroke-linejoin;miter;stroke-linecap;butt;stroke-dasharray;"12 6";stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Label00;text;__ignore__text-properties-group;;name;salgsobjekt;face-name;Tahoma,Normal;size;10;__ignore__color-group;;fill;1,0,0;opacity;1;halo-fill;1,1,1;halo-radius;0;__ignore__positioning-group;;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;;comp-op;src-over;Label;text;__ignore__text-properties-group;;name;label;face-name;Tahoma,Normal;size;@Evaluate(4*@Value(dy));__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;middle;justify-alignment;center;vertical-alignment;top;__ignore__comp-group;;comp-op;src-over;Line00;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over;X;text;__ignore__text-properties-group;;name;x;face-name;Tahoma,Normal;size;20;__ignore__color-group;;fill;0,0,1;opacity;1;halo-fill;1,1,1;halo-radius;0;__ignore__positioning-group;FME_DISCLOSURE_OPEN;text-ratio;0;wrap-width;0;wrap-before;No;spacing;0;character-spacing;0;line-spacing;0;label-position-tolerance;0;dx;-50;dy;0;avoid-edges;No;minimum-distance;0;minimum-padding;0;minimum-path-length;0;allow-overlap;No;orientation;0;placement;point;placement-type;dummy;placements;<Unused>;max-char-angle-delta;<Unused>;horizontal-alignment;auto;justify-alignment;left;vertical-alignment;auto;__ignore__comp-group;;comp-op;src-over;Y;text;__ignore__text-properties-group;;name;y;face-name;Tahoma,Normal;size;20;__ignore__color-group;;fill;0,0,1;opacity;1;halo-fill;1,1,1;halo-radius;0;__ignore__positioning-group;FME_DISCLOSURE_OPEN;text-ratio;0;wrap-width;0;wrap-before;No;spacing;0;character-spacing;0;line-spacing;0;label-position-tolerance;0;dx;0;dy;-100;avoid-edges;No;minimum-distance;0;minimum-padding;0;minimum-path-length;0;allow-overlap;No;orientation;270;placement;point;placement-type;dummy;placements;<Unused>;max-char-angle-delta;<Unused>;horizontal-alignment;auto;justify-alignment;auto;vertical-alignment;auto;__ignore__comp-group;FME_DISCLOSURE_OPEN;comp-op;src-over
    RASTER -> Clipper [CLIPPEE]
Clipper
    BOUNDARY_CASES = Treat as Inside
    CLIP_TYPE = Multiple Clippers
    CONNECT_Z_MODE = First Wins
    CLIPPED_ATTR = _clipped
    CREATE_AGGREGATES = Yes
    PRESERVE_CLIPPEE_EXTENTS = No
    LINES_AS_SEGMENTS = No
    INSIDE -> PDFPageFormatter [Inside]
PDFPageFormatter
    PAGE_WIDTH_USER = 21
    PAGE_HEIGHT_USER = 29.7
    PAGE_UNITS = Centimeters
    PAGE_OBJECTS = "Inside CLIPPING_ENABLED;No;MINY;28.45;WIDTH;538.58;MINX;28.35;HEIGHT;785.2;SIZE_PARAMS;;SCALING_PARAMS;;FIXED_ASPECT;Yes"
    PAGE_WIDTH_PTS = 595
    PAGE_HEIGHT_PTS = 842
    PAGE_NUMBER = 1
    PAGE_ORIENTATION = Portrait
    PAGE_SIZE = A4
    -> Teig (writer PDF2D_1)
Teig (writer PDF2D_1)

FME custom transformer Layout

Parameters:
- Higth =   # Hight Frame
- layout_style = V:\FME\Ambitia\Layout\Situasjonskart-topp1-1000.jpg   # Choose Layout style

Input (input)
    -> BoundsExtractor
BoundsExtractor
    XMIN = _xmin
    XMAX = _xmax
    YMIN = _ymin
    ZMIN = _zmin
    ZMAX = _zmax
    YMAX = _ymax
    -> ParameterFetcher
ParameterFetcher
    ATTR_LIST = _Higth {$(Higth)}
    -> PythonCaller
PythonCaller
    PYTHONSYMBOL = FeatureProcessor
    NEW_ATTRIBUTES = _ymin _ymax
    PYTHONSOURCE:
      import fme
      import fmeobjects
      # Template Function interface:
      def processFeature(feature):
          pass

      # Template Class Interface:
      class FeatureProcessor(object):
          def __init__(self):
              self.y0=0
              self.y1=0
          def input(self,feature):
              self.y0 = float(feature.getAttribute('_ymax'))
              self.y  = float(feature.getAttribute('_ymin'))
              self.dy=self.y0 - self.y

              self.y1=self.y0+float(feature.getAttribute('_Higth'))*self.dy/(277.0-float(feature.getAttribute('_Higth')))

              feature.setAttribute('_ymin',self.y0)
              feature.setAttribute('_ymax',self.y1)
              self.pyoutput(feature)
          def close(self):
              del self
    -> VertexCreator
VertexCreator
    MODE_NAME = Replace with Point
    YVAL = @Value(_ymin)
    XVAL = @Value(_xmin)
    -> VertexCreator_4
VertexCreator_4
    MODE_NAME = Add Point
    YVAL = @Value(_ymax)
    XVAL = @Value(_xmax)
    -> BoundsExtractor_2
BoundsExtractor_2
    XMIN = _xmin
    XMAX = _xmax
    YMIN = _ymin
    ZMIN = _zmin
    ZMAX = _zmax
    YMAX = _ymax
    -> FeatureReader_2 [INITIATOR]
Counter_2
    CNT_ATTR = id
    DOMAIN = id
    SCOPE = Local
    START = 0
    -> FeatureMerger [REQUESTOR]
Counter
    CNT_ATTR = id
    DOMAIN = id
    SCOPE = Local
    START = 0
    -> FeatureMerger [SUPPLIER]
FeatureMerger
    REJECT_NULL_MISSING_KEYS = No
    ATTR_CONFLICT_RES = Use Requestor
    IGNORE_NULLS = No
    SUPPLIERS_FIRST = No
    PROCESS_DUPS = No
    ATTR_ACCUM_MODE = Merge Supplier
    JOIN_KEYS = @Value(id) @Value(id) AUTO
    MERGE_TYPE = Attributes Only
    MERGED -> RasterGeoreferencer
RasterGeoreferencer
    POINTANDANGLE_OR_EXTENTS = Extents
    Y_UL_COORD = @Value(_ymax)
    X_LL_COORD = @Value(_xmin)
    X_UR_COORD = @Value(_xmax)
    Y_LR_COORD = @Value(_ymin)
    X_LR_COORD = @Value(_xmax)
    Y_LL_COORD = @Value(_ymin)
    X_UL_COORD = @Value(_xmin)
    Y_UR_COORD = @Value(_ymax)
    -> AttributeRemover
AttributeRemover
    REMOVE_ATTRS = _zmin,_ymin,_zmax,_xmax,pdf_page_number,_xmin,_ymax
    -> Output (output)
Output (output)

Bookmark: NB! Edit fmw in Texteditor
FeatureReader_2
    JPEG_GROUP_BY_DATASET = No
    INTERACT = <No Spatial Filter>
    DATASET = $(layout_style)
    ATTR_ACCUM_MODE = Only Use Result
    JPEG_USE_SEARCH_ENVELOPE = NO
    OUTPUT_FEATURES_DISPLAY = Schema and Data Features
    ATTRIBUTES = JPEG,exif_artist
    FORMAT = JPEG
    JPEG_CLIP_TO_ENVELOPE = NO
    JPEG_APPLY_GCPS = No
    COMBINE_GEOM = Use Result
    JPEG -> Counter_2
    INITIATOR -> Counter

FME custom transformer TextRepalcer
Adds a number layer on each side.

Parameters:
- BNR = @Value(BNR)
- FNR = @Value(FNR)
- GNR = @Value(GNR)
- SNR = @Value(SNR)
- _TEXT_HIGHT_LAYOUT =   # Text Hight Layout
- _X_DIST_LAYOUT =   # X Dist Layout
- _Y_DIST_LAYOUT_TEXT_1 =   # Y Dist Layout Text 1
- _Y_DIST_LAYOUT_TEXT_2 =   # Y Dist Layout Text 2
- _HIGTH = @Value(_Higth)   # Higth
- _SCALE = @Value(_SCALE)   # Scale

Input (input)
    -> BoundingBoxReplacer
BoundingBoxReplacer
    BOXTYPE = Bounding Box
    BOX -> BoundsExtractor
BoundsExtractor
    XMIN = _xmin
    XMAX = _xmax
    YMIN = _ymin
    YMAX = _ymax
    -> PythonCaller_2
PythonCaller_2
    PYTHONSYMBOL = FeatureProcessor
    NEW_ATTRIBUTES = _xmin _ymax _xmax _ymin text_hight
    PYTHONSOURCE:
      import fme
      import fmeobjects
      # Template Function interface:
      def processFeature(feature):
          pass

      # Template Class Interface:
      class FeatureProcessor(object):
          def __init__(self):
              pass
          def input(self,feature):
              self.y0=feature.getAttribute('_ymax')
              self.y=feature.getAttribute('_ymin')

              #The constant_y 277.0 is derived from a standing A4 with the length of 297 mm - 10 mm margin on both sides: 297-20=277
              # _High is the hight of the layout in mm.
              self.constant_y = 277.0-float(feature.getAttribute('_Higth'))
              # The constant_x 190.0 is derived from a standing A4 with the shorter length of 210 mm- 10 mm margin on both sides. 210-20=190mm
              self.constant_x = 190.0

              self.y1=self.y0+float(feature.getAttribute('_Y_DIST_LAYOUT_TEXT_1'))*(self.y0-self.y)/self.constant_y
              self.y2=self.y0+float(feature.getAttribute('_Y_DIST_LAYOUT_TEXT_2'))*(self.y0-self.y)/self.constant_y
              self.hight=float(feature.getAttribute('_TEXT_HIGHT_LAYOUT'))*(self.y0-self.y)/self.constant_y

              self.x=feature.getAttribute('_xmax')
              self.x0=feature.getAttribute('_xmin')

              self.x1=self.x0+float(feature.getAttribute('_X_DIST_LAYOUT'))*(self.x-self.x0)/self.constant_x
              #self.x2=self.x0+FME_MacroValues['x_dist_layout']*(self.x-self.x0)/190 #tidligere + 97


              feature.setAttribute('_xmin',self.x1)
              feature.setAttribute('_ymax',self.y1)
              feature.setAttribute('_ymin',self.y2)
              feature.setAttribute('_xmax',self.x1)
              feature.setAttribute('text_hight',self.hight)

              self.pyoutput(feature)
          def close(self):
              del self
    -> VertexCreator_2
    -> VertexCreator_4
VertexCreator_2
    MODE_NAME = Replace with Point
    YVAL = @Value(_ymax)
    INDEX = 0
    XVAL = @Value(_xmin)
    -> StringFormatter
StringFormatter
    SRC_ATTRS = GNR,BNR,SNR,FNR
    FORMAT = 4s
    -> AttributeCreator
AttributeCreator
    ATTR_TABLE = SET_TO gnavn = GNR: @Value(GNR) BNR: @Value(BNR) FNR: @Value(FNR) SNR: @Value(SNR)
    -> LabelPointReplacer_2
LabelPointReplacer_2
    ALWAYSROTATE = yes
    HEIGHT = @Value(text_hight)
    LABATTR = @Value(gnavn)
    LabelPoint -> Output_2 (output)
Output_2 (output)
VertexCreator_4
    MODE_NAME = Replace with Point
    YVAL = @Value(_ymin)
    INDEX = 0
    XVAL = @Value(_xmax)
    -> TimeStamper
TimeStamper
    TIME_ATTR = _timestamp
    FMT = ^d.^m.^Y
    -> AttributeCreator_2
AttributeCreator_2
    ATTR_TABLE = SET_TO _timestamp = Dato: @Value(_timestamp)        Enebakk Kommune        Målestokk: 1 : @Value(_SCALE)
    -> LabelPointReplacer_3
LabelPointReplacer_3
    ALWAYSROTATE = yes
    HEIGHT = @Value(text_hight)
    LABATTR = @Value(_timestamp)
    LabelPoint -> Dato (output)
Dato (output)

FME custom transformer SelectMapScale
Select map scale based on user published parameter

Parameters:
- _SCALE = @Value(_SCALE)   # Scale
- _HIGTH = @Value(_Higth)   # Higth

Input (input)
    -> AttributeFilter
AttributeFilter
    ATTR_NAME = _SCALE
    ATTR_VALUES = 500,1000,2000,5000,<EMPTY>,<MISSING>,<NULL>,<UNFILTERED>
    500 -> AttributeCreator_2
    1000 -> AttributeCreator
    2000 -> AttributeCreator_3
    5000 -> AttributeCreator_4
AttributeCreator_2
    ATTR_TABLE:
      SET_TO _SHORT = @real64(95)
      SET_TO _LONG = @real64(@Evaluate((277-@Value(_Higth))/2))
    -> Output (output)
AttributeCreator
    ATTR_TABLE:
      SET_TO _SHORT = 190
      SET_TO _LONG = @real64(@Evaluate((277-@Value(_Higth))))
    -> Output (output)
AttributeCreator_3
    ATTR_TABLE:
      SET_TO _SHORT = 380
      SET_TO _LONG = @real64(@Evaluate((277-@Value(_Higth))*2))
    -> Output (output)
AttributeCreator_4
    ATTR_TABLE:
      SET_TO _SHORT = 950
      SET_TO _LONG = @real64(@Evaluate((277-@Value(_Higth))*4))
    -> Output (output)
Output (output)

FME custom transformer CombinePolygonGenerators
For a simplified look

Parameters:
- _ADRESSE = @Value(_ADRESSE)   # Adresse
- _CREATION_INSTANCE = @Value(_creation_instance)   # Creation Instance
- _SCALE = @Value(_SCALE)   # Scale
- BNR = @Value(BNR)
- FNR = @Value(FNR)
- GNR = @Value(GNR)
- SNR = @Value(SNR)
- _HIGTH = @Value(_Higth)   # Higth

Input (input)
    -> StringCaseChanger
StringCaseChanger
    ATTRLIST = _ADRESSE
    CHANGE_TYPE = UPPERCASE
    ATTRCHOICE = Selected Attributes
    -> PythonCaller
PythonCaller
    PYTHONSYMBOL = FeatureProcessor
    NEW_ATTRIBUTES = TESTER GATENAVN HUSNR BOKSTAV
    PYTHONSOURCE:
      import fme
      import fmeobjects
      import re
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self.adr=feature.getAttribute('_ADRESSE')#.encode('UTF-8')
              # We split on the housenr, everythin to the left is street name if something to the right its the house letter.
              self.adr_object_list = re.split('([0-9]+)',self.adr, flags=re.IGNORECASE)
              try:
                  feature.setAttribute('TESTER',1)
                  feature.setAttribute('GATENAVN',self.adr_object_list[0].strip())
                  feature.setAttribute('HUSNR',self.adr_object_list[1])
                  feature.setAttribute('BOKSTAV',self.adr_object_list[2].strip())
              except IndexError:
                  feature.setAttribute('TESTER',0)
              self.pyoutput(feature)
          def close(self):
              pass
    -> AdressePunktGenerator
    -> TeigGenerator
TeigGenerator
    _SCALE = @Value(_SCALE)
    GNR = @Value(GNR)
    DestDataset_SQLITE3 = X:\Data\SQLITE\0229_UTVALG_EIENDOM.sl3
    FNR = @Value(FNR)
    SNR = @Value(SNR)
    BNR = @Value(BNR)
    -> A4BoundingStandingBox
    -> Clipper [CLIPPEE]
AdressePunktGenerator
    BOKSTAV = @Value(BOKSTAV)
    TESTER = @Value(TESTER)
    GATENAVN = @Value(GATENAVN)
    HUSNR = @Value(HUSNR)
    -> A4BoundingStandingBox
A4BoundingStandingBox
    Ordrenavn = 3637072.WI02290109
    TESTER = @Value(TESTER)
    _SCALE = @Value(_SCALE)
    _HIGTH = @Value(_Higth)
    -> Clipper [CLIPPER]
    -> A4BoundingBox (output)
Clipper
    ATTR_ACCUM_MODE = Merge Clipper
    BOUNDARY_CASES = Treat as Inside
    ATTR_CONFLICT_RES = Use Clippee
    CLIP_TYPE = Multiple Clippers
    CONNECT_Z_MODE = First Wins
    CLIPPED_ATTR = _clipped
    CREATE_AGGREGATES = Yes
    PRESERVE_CLIPPEE_EXTENTS = No
    LINES_AS_SEGMENTS = No
    INSIDE -> TeigGrenser (output)
TeigGrenser (output)
A4BoundingBox (output)

FME custom transformer AdressePunktGenerator

Parameters:
- HUSNR = @Value(HUSNR)
- GATENAVN = @Value(GATENAVN)
- BOKSTAV = @Value(BOKSTAV)
- TESTER = @Value(TESTER)

Input (input)
    -> Tester
Tester
    TEST_CLAUSE = TEST @Value(TESTER) = 1
    BOOL_OP = OR
    TEST_MODE = Automatic
    TEST_DESCRIPTION = ""
    PASSED -> WorkspaceRunner_3
    FAILED -> Rejected (output)
WorkspaceRunner_3
    WORKSPACE_FILE = V:\FME\Ambitia\UTVALG_ADRESSE.fmw
    BLOCKING = Yes
    WORKSPACE_PARAMETERS = ADRESSE,KLOKKERUDÅSEN 25 N,DestDataset_SQLITE3,V:\FME\Ambitia\address_temp.sl3
    SUCCEEDED -> FeatureReader_2 [INITIATOR]
    FAILED -> Rejected (output)
FeatureReader_2
    INTERACT = <No Spatial Filter>
    DATASET = V:\FME\Ambitia\address_temp.sl3
    ATTR_ACCUM_MODE = Only Use Result
    OUTPUT_FEATURES_DISPLAY = Schema and Data Features
    ATTRIBUTES = dbo_ADRESSE,"NORD,OST,ADRESSE"
    FORMAT = SPATIALITE
    FEATURETYPES = dbo_ADRESSE
    SPATIALITE_QUERY_FEATURE_TYPES_FOR_MERGE_FILTERS = Yes
    COMBINE_GEOM = Use Result
    dbo_ADRESSE -> FFeatureMerge [Requestor]
    INITIATOR -> FFeatureMerge [Supplier]
    <REJECTED> -> Rejected (output)
FFeatureMerge
    FMerged -> AttributeCreator
AttributeCreator
    ATTR_TABLE = SET_TO TESTER = 1
    -> VertexCreator
VertexCreator
    MODE_NAME = Replace with Point
    YVAL = @Value(NORD)
    XVAL = @Value(OST)
    -> Output (output)
Output (output)
Rejected (output)

FME custom transformer CombineFrameAndLayout

Parameters:
- layout_style = V:\FME\Ambitia\Layout\Situasjonskart-topp1-1000.jpg   # Choose Layout style
- Higth = 24   # Hight Frame

Input (input)
    -> Layout
    -> Frame
Layout
    Higth = $(Higth)
    layout_style = $(layout_style)
    -> Frame
    -> Layout (output)
Frame
    -> Frame (output)
Frame (output)
Layout (output)

FME custom transformer FFeatureMerge
Forces to features to merge unconditionally

Requestor (input)
    -> AttributeCreator
AttributeCreator
    ATTR_TABLE = SET_TO c = 1
    -> FeatureMerger [REQUESTOR]
Supplier (input)
    -> AttributeCreator_2
AttributeCreator_2
    ATTR_TABLE = SET_TO c = 1
    -> FeatureMerger [SUPPLIER]
FeatureMerger
    REJECT_NULL_MISSING_KEYS = No
    ATTR_CONFLICT_RES = Use Requestor
    IGNORE_NULLS = No
    SUPPLIERS_FIRST = No
    PROCESS_DUPS = No
    ATTR_ACCUM_MODE = Merge Supplier
    JOIN_KEYS = @Value(c) @Value(c) AUTO
    MERGE_TYPE = Attributes Only
    MERGED -> FMerged (output)
FMerged (output)

FME custom transformer TeigGenerator

Parameters:
- FNR = @Value(FNR)
- SNR = @Value(SNR)
- GNR = @Value(GNR)
- BNR = @Value(BNR)
- _SCALE = @Value(_SCALE)   # Scale
- DestDataset_SQLITE3 = X:\Data\SQLITE\0229_UTVALG_EIENDOM.sl3   # Destination SQLite Database File

Input (input)
    -> WorkspaceRunner
WorkspaceRunner
    WORKSPACE_FILE = V:\FME\Ambitia\UTVALG_EIENDOM.fmw
    BLOCKING = Yes
    WORKSPACE_PARAMETERS = GNR,@Value(GNR),BNR,@Value(BNR),FNR,@Value(FNR),SNR,@Value(SNR),DestDataset_SQLITE3,$(DestDataset_SQLITE3)
    SUCCEEDED -> FeatureReader [INITIATOR]
    FAILED -> WorkspaceRunner_2
WorkspaceRunner_2
    WORKSPACE_FILE = V:\FME\Ambitia\UTVALG_EIENDOM.fmw
    BLOCKING = Yes
    WORKSPACE_PARAMETERS = GNR,@Value(GNR),BNR,@Value(BNR),FNR,@Value(FNR),SNR,0,DestDataset_SQLITE3,$(DestDataset_SQLITE3)
    SUCCEEDED -> FeatureReader [INITIATOR]
    FAILED -> Terminator_2
FeatureReader
    INTERACT = <No Spatial Filter>
    DATASET = $(DestDataset_SQLITE3)
    ATTR_ACCUM_MODE = Only Use Result
    OUTPUT_FEATURES_DISPLAY = Schema and Data Features
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    FORMAT = SPATIALITE
    FEATURETYPES = Teig
    SPATIALITE_QUERY_FEATURE_TYPES_FOR_MERGE_FILTERS = Yes
    COMBINE_GEOM = Use Result
    Teig -> FFeatureMerge [Requestor]
    INITIATOR -> FFeatureMerge [Supplier]
    <REJECTED> -> Terminator_2
FFeatureMerge
    FMerged -> AttributeCreator
AttributeCreator
    ATTR_TABLE = SET_TO TESTER = 2
    -> Output (output)
Output (output)
Terminator_2
    MESSAGE = Translation Terminated Can not read @Value(GNR)-@Value(BNR)-@Value(FNR)-0 from source $(DestDataset_SQLITE3)

FME custom transformer Frame

Input (input)
    -> BoundingBoxAccumulator
BoundingBoxAccumulator
    ACCUM_ATTRS_NAME = Get Attributes From One Representative Feature
    TOPFER_INDEX = No
    BOUNDING_BOX -> GeometryCoercer
GeometryCoercer
    KIND = fme_line
    GQUERY:
      for $geom in //geometry
      where $geom/count(parent::geometry) = 0
      return number($geom/@fme_id)
    COERCED -> BoundsExtractor
BoundsExtractor
    XMIN = xmin_extent
    XMAX = xmax_extent
    YMIN = ymin_extent
    YMAX = ymax_extent
    -> Output (output)
Output (output)

FME custom transformer MeasureLineCreator

Input (input)
    -> BoundsExtractor
BoundsExtractor
    XMIN = _xmin
    XMAX = _xmax
    YMIN = _ymin
    YMAX = _ymax
    -> AttributeCreator
AttributeCreator
    ATTR_TABLE:
      SET_TO size = @ceil(@Evaluate(@Value(_xmax)-@Value(_xmin))/5)
      SET_TO dy = @floor(@Evaluate((@Value(_ymax)-@Value(_ymin))/15))
      SET_TO dx = @floor(@Evaluate((@Value(_ymax)-@Value(_ymin))/15))
    -> TestFilter
TestFilter
    TEST_LIST:
      BOOL_OP,AND,COMPOSITE_TEST,<Unused>,TEST_CLAUSE,"TEST @Value(size) >= 0
      TEST @Value(size) < 100",< 100,BOOL_OP,AND,COMPOSITE_TEST,<Unused>,TEST_CLAUSE,"TEST @Value(size) >= 100
      TEST @Value(size) < 1000",< 1000,BOOL_OP,AND,COMPOSITE_TEST,<Unused>,TEST_CLAUSE,"TEST @Value(size) >= 1000
      TEST @Value(size) < 10000",< 10000,BOOL_OP,AND,COMPOSITE_TEST,<Unused>,TEST_CLAUSE,"TEST @Value(size) >= 10000
      TEST @Value(size) < 100000",< 100000
    DEFAULT_VALUE = <UNFILTERED>
    < 100 -> AttributeRounder
    < 1000 -> AttributeRounder_2
    < 10000 -> AttributeRounder_3
    < 100000 -> AttributeRounder_4
AttributeRounder
    PLACES = -1
    SRC_ATTRS = size
    ROUND_TYPE = Nearest
    -> VertexCreator
AttributeRounder_2
    PLACES = -2
    SRC_ATTRS = size
    ROUND_TYPE = Nearest
    -> VertexCreator
VertexCreator
    MODE_NAME = Replace with Point
    YVAL = @Evaluate(@Value(_ymin)+@Value(dy))
    XVAL = @Evaluate(@Value(_xmax)-@Value(dx))
    -> VertexCreator_2
    -> VertexCreator_5
VertexCreator_5
    MODE_NAME = Add Point
    YVAL = @Evaluate(@Value(_ymin)+2*@Value(dy))
    XVAL = @Evaluate(@Value(_xmax)-@Value(dx))
    -> Line (output)
VertexCreator_2
    MODE_NAME = Add Point
    YVAL = @Evaluate(@Value(_ymin)+@Value(dy))
    XVAL = @Evaluate(@Value(_xmax)-@Value(dx)-@Value(size))
    -> AttributeCreator_2
    -> VertexCreator_6
VertexCreator_6
    MODE_NAME = Add Point
    YVAL = @Evaluate(@Value(_ymin)+2*@Value(dy))
    XVAL = @Evaluate(@Value(_xmax)-@Value(dx)-@Value(size))
    -> Line (output)
AttributeCreator_2
    ATTR_TABLE = SET_TO BENEVNING = m
    -> AttributeCreator_4
    -> Line (output)
Line (output)
AttributeRounder_3
    PLACES = -3
    SRC_ATTRS = size
    ROUND_TYPE = Nearest
    -> VertexCreator_3
AttributeRounder_4
    PLACES = -4
    SRC_ATTRS = size
    ROUND_TYPE = Nearest
    -> VertexCreator_3
VertexCreator_3
    MODE_NAME = Replace with Point
    YVAL = @Evaluate(@Value(_ymin)+@Value(dy))
    XVAL = @Evaluate(@Value(_xmax)-@Value(dx))
    -> VertexCreator_4
VertexCreator_4
    MODE_NAME = Add Point
    YVAL = @Evaluate(@Value(_ymin)+@Value(dy))
    XVAL = @Evaluate(@Value(_xmax)-@Value(dx)-@Value(size))
    -> AttributeCreator_3
AttributeCreator_3
    ATTR_TABLE:
      SET_TO BENEVNING = Km
      SET_TO size = @Evaluate(@Value(size)/1000)
    -> AttributeCreator_4
AttributeCreator_4
    ATTR_TABLE = SET_TO label = @int(@Value(size))@Value(BENEVNING)
    -> LabelPointReplacer
LabelPointReplacer
    ALWAYSROTATE = yes
    HEIGHT = @Evaluate(2*@Value(dy))
    LABATTR = @Value(label)
    LabelPoint -> Label (output)
Label (output)

FME custom transformer MerkEiendom

Parameters:
- _gnr = 115   # Gnr
- _bnr = 312   # Bnr
- _fnr = 0   # Fnr
- _snr = 0   # Snr

Input (input)
    -> DonutHoleExtractor
    -> Polygon (output)
DonutHoleExtractor
    OUTERSHELL -> GeometryCoercer
    HOLE -> GeometryCoercer
GeometryCoercer
    KIND = fme_line
    GQUERY:
      for $geom in //geometry
      where $geom/count(parent::geometry) = 0
      return number($geom/@fme_id)
    COERCED -> AttributeCreator
    COERCED -> Line (output)
AttributeCreator
    ATTR_TABLE = SET_TO salgsobjekt = Eiendomsgrenser
    -> Chopper
Chopper
    MODE = By Length
    CHOPPED_ATTR = _chopped
    APPROX_LENGTH = 50
    GRID_AREAS = Yes
    -> OrientationExtractor
OrientationExtractor
    ORIENTATION = _orientation
    -> LabelPointReplacer
LabelPointReplacer
    ALWAYSROTATE = no
    HEIGHT = 20
    LABATTR = @Value(salgsobjekt)
    LabelPoint -> label (output)
label (output)
Line (output)
Polygon (output)

FME custom transformer GridCreator

Note: Setter extend for en A4 med sidemarger på 1,6cm, toppmarg på 2,69 cm og bunnmarg på 1,89 cm / Opprinnelig A4-mål = 21.0cm X 29.7 cm
2DGridCreator_2 [off]
    NUMROWS = 300
    STARTINGX = 600000
    STARTINGY = 6600000
    YINC = 100
    GRID_TYPE = Polygons
    COL_ATTR = _column
    XINC = 100
    ROW_ATTR = _row
    NUMCOLS = 600
    STARTINGCORNER = Lower Left
Input (input)
    -> BoundsExtractor
    -> Clipper [CLIPPER]
BoundsExtractor
    XMIN = _xmin
    XMAX = _xmax
    YMIN = _ymin
    ZMIN = _zmin
    ZMAX = _zmax
    YMAX = _ymax
    -> PythonCaller
PythonCaller
    PYTHONSYMBOL = FeatureProcessor
    NEW_ATTRIBUTES = _xmin _ymin _xmax _ymax
    PYTHONSOURCE:
      import fme
      import fmeobjects
      import math
      def rounddown(x):
          return int(math.floor(x / 100.0)) * 100
      def roundup(x):
          return int(math.ceil(x / 100.0)) * 100
      # Template Function interface:
      def processFeature(feature):
          pass

      # Template Class Interface:
      class FeatureProcessor(object):
          def __init__(self):
              pass
          def input(self,feature):
              feature.setAttribute('_xmin',rounddown(feature.getAttribute('_xmin')))
              feature.setAttribute('_ymin',rounddown(feature.getAttribute('_ymin')))
              feature.setAttribute('_xmax',roundup(feature.getAttribute('_xmax')))
              feature.setAttribute('_ymax',roundup(feature.getAttribute('_ymax')))

              self.pyoutput(feature)
          def close(self):
              pass
    -> VertexCreator
VertexCreator
    MODE_NAME = Replace with Point
    YVAL = @Value(_ymin)
    INDEX = 0
    XVAL = @Value(_xmin)
    -> VertexCreator_2
VertexCreator_2
    MODE_NAME = Add Point
    YVAL = @Value(_ymax)
    INDEX = 0
    XVAL = @Value(_xmax)
    -> BoundingBoxReplacer
BoundingBoxReplacer
    BOXTYPE = Bounding Box
    BOX -> 2DGridAccumulator
2DGridAccumulator
    YINC = 100
    GRID_TYPE = Polygons
    COL_ATTR = _column
    SIZE_TYPE = Cell Size
    XINC = 100
    ROW_ATTR = _row
    STARTINGCORNER = Lower Left
    GRID -> Clipper [CLIPPEE]
Clipper
    ATTR_PREFIX = clipper_
    BOUNDARY_CASES = Treat as Inside
    CLIP_TYPE = Multiple Clippers
    CLIPPED_ATTR = _clipped
    CREATE_AGGREGATES = Yes
    PRESERVE_CLIPPEE_EXTENTS = No
    MERGE_ATTRS = No
    INSIDE -> Chopper
Chopper
    MODE = By Vertex
    CHOPPED_ATTR = _chopped
    REMNANT_ATTR = _remnant
    MAX_VERTICES = 2
    -> CoordinateExtractor_2
CoordinateExtractor_2
    IND = 0
    Y_ATTR = _y
    X_ATTR = _x
    Z_ATTR = _z
    Z_DEFAULT = -9999
    -> CoordinateExtractor_3
CoordinateExtractor_3
    IND = 1
    Y_ATTR = _y1
    X_ATTR = _x1
    Z_ATTR = _z
    Z_DEFAULT = -9999
    -> Tester
Tester
    TEST_CLAUSE:
      TEST @Value(_x) ENDS_WITH 00
      TEST @Value(_y) ENDS_WITH 00
    BOOL_OP = AND
    TEST_MODE = Automatic
    TEST_DESCRIPTION = ""
    PASSED -> VertexCreator_3
VertexCreator_3
    MODE_NAME = Replace with Point
    YVAL = @Value(_y)
    INDEX = 0
    XVAL = @Value(_x)
    -> VertexCreator_4
VertexCreator_4
    MODE_NAME = Add Point
    YVAL = @Value(_y1)
    INDEX = 0
    XVAL = @Value(_x1)
    -> AttributeCreator_3
AttributeCreator_3
    ATTR_LIST = fme_color,0,0,1,x,X@Value(_y),y,Y@Value(_x)
    -> Counter
    -> AttributeCreator
AttributeCreator
    ATTR_LIST = fme_color,0,0,1
    -> Line (output)
Line (output)
Counter
    CNT_ATTR = layer
    DOMAIN = counter
    SCOPE = Local
    START = 2
    -> Labeller
    -> Labeller_2
Labeller_2
    TANROTATTR = _label_rotation
    SPACE = 50
    AVERAGE_CHAR_WIDTH = 0.0
    SPOT_CHOICE = Above or Right
    MIN = 10
    DIST = 0.5
    OVERLAPS = Yes
    ENDS = yes
    HEIGHT = 3
    PARROTATTR = _parallel_rotation
    LABATTR = @Value(x)
    LABEL -> X
X: Tester
    TEST_CLAUSE:
      TEST @Value(_parallel_rotation) = 90
      TEST @Value(_parallel_rotation) = 270
    BOOL_OP = OR
    TEST_MODE = Automatic
    TEST_DESCRIPTION = ""
    PASSED -> X (output)
X (output)
Labeller
    TANROTATTR = _label_rotation
    SPACE = 50
    AVERAGE_CHAR_WIDTH = 0.0
    SPOT_CHOICE = Above or Right
    MIN = 10
    DIST = 0.5
    OVERLAPS = Yes
    ENDS = yes
    HEIGHT = 3
    PARROTATTR = _parallel_rotation
    LABATTR = @Value(y)
    LABEL -> Y
Y: Tester
    TEST_CLAUSE:
      TEST @Value(_parallel_rotation) = 90
      TEST @Value(_parallel_rotation) = 270
    BOOL_OP = OR
    TEST_MODE = Automatic
    TEST_DESCRIPTION = ""
    FAILED -> Y (output)
Y (output)

FME custom transformer WMS_3

Parameters:
- WMS_url =
- WMS_layer =
- Username =   # Enter Username
- password =   # Enter password

Input (input)
    -> BoundsExtractor_3
BoundsExtractor_3
    XMIN = _xmin
    XMAX = _xmax
    YMIN = _ymin
    YMAX = _ymax
    -> PythonCaller
PythonCaller
    PYTHONSYMBOL = FeatureProcessor
    NEW_ATTRIBUTES = width height
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self._xmax=0
              self._xmin=0
              self._ymax=0
              self._ymin=0
              self.width=0
              self.height=0
              self.return_height=0
              self.return_width=0
              self.wms_constant=4096

          def input(self,feature):
              self._xmax=float(feature.getAttribute('_xmax'))
              self._xmin=float(feature.getAttribute('_xmin'))
              self._ymax=float(feature.getAttribute('_ymax'))
              self._ymin=float(feature.getAttribute('_ymin'))

              self.width=self._xmax - self._xmin
              self.height=self._ymax - self._ymin

              # wms_constant is the maximun of allowed pixel to be requested
              self.wms_constant=4096
              if self.height > self.width:
                  self.return_height = self.wms_constant
                  self.return_width  = self.wms_constant/(self.height/self.width)
              elif self.height < self.width:
                  self.return_width  = self.wms_constant
                  self.return_height = self.wms_constant/(self.width/self.height)
              elif self.height == self.width:
                  self.return_width  = self.wms_constant
                  self.return_height = self.wms_constant
              else:
                  raise ValueError("Python Caller in WMS_3 got an unexpected result")

              feature.setAttribute('width', int(round(self.return_width)) )
              feature.setAttribute('height', int(round(self.return_height)) )
              self.pyoutput(feature)
          def close(self):
              del self
              pass
    -> AttributeCreator_3
AttributeCreator_3
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Value(width)&HEIGHT=@Value(height)&SRS=EPSG:25832&TRANSPARENT=true&BBOX=@Value(_xmin),@Value(_ymin),@Value(_xmax),@Value(_ymax)&253
    -> HTTPCaller_2
HTTPCaller_2
    TARGET_URL = @Value(_wms2)
    ERROR_ATTR = _error
    AUTH_PASSWORD = $(password)
    TARGET_ATTR_ENCODING = auto-detect
    FOLLOW_REDIRECTS = Yes
    RESPONSE_HEADER_LIST_ATTR = _headers
    TARGET_ATTR = _response_body
    HTTP_METHOD = GET
    TRANSFER_TIMEOUT_LENGTH = 90
    CONNECTION_TIMEOUT_LENGTH = 60
    SAVE_FILE = Attribute
    STATUS_CODE_ATTR = _http_status_code
    VERIFY_SSL_CERTIFICATES = Yes
    AUTH_USERNAME = $(Username)
    USE_COOKIES = No
    AUTH_METHOD = Basic
    -> RasterReplacer_2
RasterReplacer_2
    REMOVE_ATTRIBUTE = No
    FORMAT = PNGRASTER
    BLOB_ATTR = _response_body
    -> RasterCheckpointer
RasterCheckpointer
    -> RasterGeoreferencer_2
RasterGeoreferencer_2
    POINTANDANGLE_OR_EXTENTS = Extents
    Y_UL_COORD = @Value(_ymax)
    X_LL_COORD = @Value(_xmin)
    X_UR_COORD = @Value(_xmax)
    Y_LR_COORD = @Value(_ymin)
    X_LR_COORD = @Value(_xmax)
    Y_LL_COORD = @Value(_ymin)
    X_UL_COORD = @Value(_xmin)
    Y_UR_COORD = @Value(_ymax)
    -> AttributeRemover_2
AttributeRemover_2
    REMOVE_ATTRS = _ymax,_xmax,_ymin,_wms,_wms2,dv,_http_status_code,_xmin,dh,_response_body
    LIST_ATTRS = _headers{} _headers{}.name _headers{}.value
    -> RasterCheckpointer_2
RasterCheckpointer_2
    -> RasterMosaicker
RasterMosaicker
    SNAPPING_TYPE_NAME = Resample
    NODATA_OVERWRITE = No
    MERGE_PALETTES_NAME = Yes
    COMPOSITE_USING_ALPHA_BAND_NAME = No
    INTERPOLATION_TYPE_NAME = Nearest Neighbor
    ACCUM_ATTRS_NAME = Get Attributes From One Representative Feature
    -> Output (output)
Output (output)

FME custom transformer A4BoundingStandingBox
Calculates a A4 bounding box

Parameters:
- Ordrenavn = 3637072.WI02290109
- TESTER = @Value(TESTER)
- _SCALE = @Value(_SCALE)   # Scale
- _HIGTH = @Value(_Higth)   # Higth

Input (input)
    -> SelectMapScale
SelectMapScale
    _SCALE = @Value(_SCALE)
    _HIGTH = @Value(_Higth)
    -> Sorter
Sorter
    SORT_PARM = TESTER NUMERIC ASCENDING
    SORTED -> Sampler
Sampler
    RATE = 1
    SAMPLE_MODE = No
    SAMPLE_TYPE_LONG = First N Features
    SAMPLED -> GeometryFilter
GeometryFilter
    BREAK_AGG = No
    GEOM_PORT_NAMES = Point Area
    POINT -> CoordinateExtractor
    AREA -> CenterPointReplacer
CenterPointReplacer
    MODE = Center Point
    POINT -> CoordinateExtractor
CoordinateExtractor
    MODE = Specify Coordinate
    IND = 0
    Y_ATTR = NORD
    X_ATTR = OST
    -> AttributeCreator_3
AttributeCreator_3
    ATTR_LIST = xmin,@Evaluate(@Value(OST)-@Value(_SHORT)/2),xmax,@Evaluate(@Value(OST)+@Value(_SHORT)/2),ymin,@Evaluate(@Value(NORD)-@Value(_LONG)/2),ymax,@Evaluate(@Value(NORD)+@Value(_LONG)/2)
    -> VertexCreator_2
VertexCreator_2
    MODE_NAME = Replace with Point
    YVAL = @Value(ymin)
    INDEX = 0
    XVAL = @Value(xmin)
    -> VertexCreator_3
VertexCreator_3
    MODE_NAME = Add Point
    YVAL = @Value(ymax)
    INDEX = 0
    XVAL = @Value(xmax)
    -> BoundingBoxReplacer_3
BoundingBoxReplacer_3
    BBSHORTER = 210
    BOXTYPE = Bounding Box
    BBLONGER = 297
    BOX -> Output (output)
Output (output)
