FME workspace UTVALG_EIENDOM.fmw

Parameters:
- GNR = 115
- BNR = 232
- FNR = 0
- SNR = 0
- DestDataset_SQLITE3 = X:\Data\SQLITE\0229_UTVALG_EIENDOM.sl3   # Destination SQLite Database File

Readers:
- SQLITE3_1: SQLITE3 from X:\Data\SQLITE\0229_EIENDOM.SL3

Writers:
- SQLITE3_2: SQLITE3 to $(DestDataset_SQLITE3)

Teig (reader SQLITE3_1)
    attributes: PRIMARYINDEX integer, Geometry blob, BEREGNETAREAL_AREAL float, BEREGNETAREAL_AREALMERKNAD text, BEREGNETAREAL_AREALMERKNAD{}_AREALMERKNAD text, AREALKILDE text, HOVEDTEIG text, MATRID_MATRIKKELENHET text, MATRIKKELENHETSTYPE text, BNR text, FNR text, GNR text, SNR text, TINGLYST text, TEIG-ID float, TEIGMEDFLEREMATRENHETER text
    -> Teig (writer SQLITE3_2)
    -> AttributeCreator
Teig (writer SQLITE3_2)
    attributes: PRIMARYINDEX integer, Geometry blob, BEREGNETAREAL_AREAL float, BEREGNETAREAL_AREALMERKNAD text, BEREGNETAREAL_AREALMERKNAD{}_AREALMERKNAD text, AREALKILDE text, HOVEDTEIG text, MATRID_MATRIKKELENHET text, MATRIKKELENHETSTYPE text, BNR text, FNR text, GNR text, SNR text, TINGLYST text, TEIG-ID float, TEIGMEDFLEREMATRENHETER text
spatial_ref_sys (reader SQLITE3_1)
    attributes: srid integer, sr_name text, auth_name text, auth_srid integer, srtext text, sr_xytol float, sr_ztol float
    -> spatial_ref_sys (writer SQLITE3_2)
spatial_ref_sys (writer SQLITE3_2)
    attributes: srid integer, sr_name text, auth_name text, auth_srid integer, srtext text, sr_xytol float, sr_ztol float
geometry_columns (reader SQLITE3_1)
    attributes: f_table_name text, f_geometry_column text, geometry_type integer, geometry_dettype integer, coord_dimension integer, srid integer, geometry_format text
    -> geometry_columns (writer SQLITE3_2)
geometry_columns (writer SQLITE3_2)
    attributes: f_table_name text, f_geometry_column text, geometry_type integer, geometry_dettype integer, coord_dimension integer, srid integer, geometry_format text
Creator
    NUM = 1
    GEOMTYPE = Geometry Object
    CREATED -> AttributeCreator
AttributeCreator
    ATTR_TABLE = SET_TO ID = 1
    -> StatisticsCalculator
StatisticsCalculator
    STATS_ATTRS = ID
    PREPEND_ATTR_NAME_CHOICE = For multiple results only
    COMPUTE_HISTOGRAM = NO
    NUMERIC_ATTR = _numeric_count
    COUNT_ATTR = _count
    SUMMARY -> Tester
Tester
    TEST_CLAUSE = TEST @Value(_count) = 1
    BOOL_OP = OR
    TEST_MODE = Automatic
    TEST_DESCRIPTION = ""
    PASSED -> Terminator
Terminator
    MESSAGE = Translation Terminated
