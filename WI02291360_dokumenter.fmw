FME workspace WI02291360_dokumenter.fmw

Parameters:
- GNR = 115
- BNR = 232
- FNR = 0
- SNR = 0
- filecopy_dest_filename = Ordreid   # " " filecopy_dest_filename
- DestDataset_FILECOPY = $(FME_MF_DIR)ftp\upload   # Destination File Copy Folder
- Bestemmelser = X:\Data\planregister\0229\GjeldendeBestemmelser   # Sti til bestemmelser
- DestDataset_SPATIALITE = X:\Data\SQLITE\0229_UTVALG_EIENDOM.sl3   # Destination SpatiaLite Database File
- Andredok = X:\Data\planregister\0229\AndreDokumenter   # Sti til andre dokumenter

Writers:
- FILECOPY_1: FILECOPY to $(DestDataset_FILECOPY)

Creator
    NUM = 1
    GEOMTYPE = Geometry Object
    CREATED -> WorkspaceRunner
WorkspaceRunner
    BLOCKING = Yes
    WORKSPACE_FILE = $(FME_MF_DIR)UTVALG_EIENDOM.fmw
    WORKSPACE_PARAMETERS = GNR,$(GNR),BNR,$(BNR),FNR,$(FNR),SNR,$(SNR),DestDataset_SQLITE3,$(DestDataset_SPATIALITE)
    SUCCEEDED -> FeatureReader [INITIATOR]
FeatureReader
    INTERACT = <No Spatial Filter>
    SPATIALITE_QUERY_FEATURE_TYPES_FOR_MERGE_FILTERS = Yes
    COMBINE_GEOM = Use Result
    DATASET = $(DestDataset_SPATIALITE)
    COORDSYS = EPSG:25832
    OUTPUT_FEATURES_DISPLAY = Schema and Data Features
    ATTR_ACCUM_MODE = Only Use Result
    FORMAT = SPATIALITE
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    Teig -> Clipper [CLIPPER]
Creator_2
    NUM = 1
    GEOMTYPE = Geometry Object
    CREATED -> FeatureReader_2 [INITIATOR]
FeatureReader_2
    INTERACT = <No Spatial Filter>
    GDMMAPPERQUADRI_GDMR_ACCEPT2DPOINTSIN3DFEATURES = no
    GDMMAPPERQUADRI_GDMR_ONEFEATURETYPEONLY = NO
    GDMMAPPERQUADRI_GDMR_READENVELOPE = NO
    GDMMAPPERQUADRI_GDMR_CONVERTARCTOVECTORS = no
    FEATURETYPES = KpArealformålOmråde KpOmråde
    GDMMAPPERQUADRI_GDMR_CHECKATTRIBTYPESACROSSFEATURES = no
    GDMMAPPERQUADRI_GDMR_VERSION = 411
    COMBINE_GEOM = Use Result
    GDMMAPPERQUADRI_GDMR_USEFFSCACHE = yes
    DATASET = X:\Data\QUADRI\0229_KP3.GDD
    GDMMAPPERQUADRI_GDMR_STOREOBJECTCODETOFME = no
    COORDSYS = EPSG:25832
    GDMMAPPERQUADRI_GDMR_USESSOSIATTRIBDEFS = no
    GDMMAPPERQUADRI_GDMR_ADDTHEMECODE = no
    GDMMAPPERQUADRI_GDMR_ADDGEOMETRYATTRIBUTES = no
    OUTPUT_FEATURES_DISPLAY = Schema and Data Features
    ATTR_ACCUM_MODE = Only Use Result
    GDMMAPPERQUADRI_GDMR_LISTATTRIBSASFMELISTS = 3
    GDMMAPPERQUADRI_GDMR_CLIPTOENVELOPE = yes
    GDMMAPPERQUADRI_GDMR_STOREGDMSURFACEASFMEPOINT = no
    GDMMAPPERQUADRI_GDMR_CONVERTPOINTATTRIBSTOPOINTS = no
    GDMMAPPERQUADRI_GDMR_MAXGAP = .2
    GDMMAPPERQUADRI_GDMR_ADDOBJTYPEATTRIBUTE = yes
    GDMMAPPERQUADRI_GDMR_READTOPOLOGY = no
    GDMMAPPERQUADRI_GDMR_KEEPGEOMETRYONTEXTS = no
    FORMAT = GDMMAPPERQUADRI
    ATTRIBUTES = KpAngittHensynGrense,"FØRSTEDIGITALISERINGSDATO,GEOMETRITYPE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpAngittHensynSone,"BESKRIVELSE,FTEMA,FØRSTEDIGITALISERINGSDATO,GEOMETRITYPE,HENSYNSONENAVN,KPANGITTHENSYN,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpArealGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpArealformålOmråde,"AREALST,BESKRIVELSE,EIERFORM,FTEMA,FØRSTEDIGITALISERINGSDATO,GEOMETRITYPE,KPAREALFORMÅL,NASJONALAREALPLANID.KOMM,NASJONALAREALPLANID.PLANID,OBJTYPE,OMRNAVN,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpBestemmelseGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpBestemmelseOmråde,"BESTEMMELSEOMRNAVN,FTEMA,FØRSTEDIGITALISERINGSDATO,GEOMETRITYPE,KPBESTEMMELSEHJEMMEL,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpBåndleggingGrense,"AREALST,FØRSTEDIGITALISERINGSDATO,GEOMETRITYPE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpBåndleggingSone,"AREALST,BESKRIVELSE,FTEMA,FØRSTEDIGITALISERINGSDATO,GEOMETRITYPE,HENSYNSONENAVN,KPBÅNDLEGGING,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpFareGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpFareSone,"FTEMA,FØRSTEDIGITALISERINGSDATO,GEOMETRITYPE,HENSYNSONENAVN,KPFARE,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpJuridiskLinje,"FØRSTEDIGITALISERINGSDATO,GEOMETRITYPE,KPJURLINJE,KVALITET.MÅLEMETODE,LTEMA,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpOmråde,"FTEMA,FØRSTEDIGITALISERINGSDATO,GEOMETRITYPE,IKRAFT,LOVREFERANSE,NASJONALAREALPLANID.KOMM,NASJONALAREALPLANID.PLANID,OBJTYPE,OPPDATERINGSDATO,PLANBEST,PLANNAVN,PLANSTAT,PLANTYPE,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpPåskrift,"FEATURE_ID,FØRSTEDIGITALISERINGSDATO,GEOMETRITYPE,NASJONALAREALPLANID.KOMM,NASJONALAREALPLANID.PLANID,OBJTYPE,OPPDATERINGSDATO,PLANPÅSKRIFTTYPE,TEKST.FØLGER-LINJE,TEKST.RETNING-NORD,TEKST.RETNING-ØST,TEKST.START-NORD,TEKST.START-ØST,TEKST.STRENG,TTEMA,_original_geometry,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpSamferdselLinje,"AREALST,FØRSTEDIGITALISERINGSDATO,GEOMETRITYPE,KVALITET.MÅLEMETODE,LTEMA,NASJONALAREALPLANID.KOMM,NASJONALAREALPLANID.PLANID,OBJTYPE,OPPDATERINGSDATO,TYPESAMFLINJE,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpSikringGrense,"GEOMETRITYPE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpSikringSone,"BESKRIVELSE,FTEMA,GEOMETRITYPE,HENSYNSONENAVN,KPSIKRING,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpStøyGrense,"GEOMETRITYPE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",KpStøySone,"FTEMA,FØRSTEDIGITALISERINGSDATO,GEOMETRITYPE,HENSYNSONENAVN,KPSTØY,NASJONALAREALPLANID.KOMM,NASJONALAREALPLANID.PLANID,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}"
    GDMMAPPERQUADRI_GDMR_ADDFMETEXTS = no
    KpOmråde -> Clipper [CLIPPEE]
Clipper
    CLIPPED_ATTR = _clipped
    BOUNDARY_CASES = Treat as Inside
    ATTR_ACCUM_MODE = Merge Clipper
    CONNECT_Z_MODE = First Wins
    LINES_AS_SEGMENTS = No
    CLIP_TYPE = Multiple Clippers
    PRESERVE_CLIPPEE_EXTENTS = No
    CREATE_AGGREGATES = Yes
    ATTR_CONFLICT_RES = Use Clippee
    INSIDE -> DuplicateFilter
DuplicateFilter
    INPUT_ORDERED_CHOICE = No
    KEYATTR = NASJONALAREALPLANID.PLANID
    UNIQUE -> Joiner_2
Joiner_2
    PREFETCH_EXHAUSTIVE = Yes
    DATASET = 0229Planregister
    ATTR_ACCUM_MODE = Merge Joined
    JOIN_KEYS = NASJONALAREALPLANID.PLANID Planid
    MSSQL_ADO_NAMED_CONNECTION = 0229Planregister
    MATCH_MULTIPLE_DISPLAY = Create a feature for each match
    ATTR_CONFLICT_RES = Use Original
    CACHE_SIZE = 5000
    TABLE = dbo.Arealplan
    ADDED_FIELDS = PlanBestemmelser PlanType
    MSSQL_ADO_COMMAND_TIMEOUT = 30
    MATCH_RULE_DISPLAY = Match All (1:M)
    MSSQL_ADO_QUERY_FEATURE_TYPES_FOR_MERGE_FILTERS = Yes
    FORMAT = MSSQL_ADO
    JOINED -> Joiner
Joiner
    PREFETCH_EXHAUSTIVE = Yes
    DATASET = 0229Planregister
    ATTR_ACCUM_MODE = Merge Joined
    JOIN_KEYS = NASJONALAREALPLANID.PLANID Planid
    MSSQL_ADO_NAMED_CONNECTION = 0229Planregister
    MATCH_MULTIPLE_DISPLAY = Create a feature for each match
    ATTR_CONFLICT_RES = Use Original
    CACHE_SIZE = 5000
    TABLE = dbo.DokumenterPlan
    ADDED_FIELDS = DokPlanId Dokumentid
    MSSQL_ADO_COMMAND_TIMEOUT = 30
    MATCH_RULE_DISPLAY = Match All (1:M)
    MSSQL_ADO_QUERY_FEATURE_TYPES_FOR_MERGE_FILTERS = Yes
    FORMAT = MSSQL_ADO
    JOINED -> Joiner_3
Joiner_3
    PREFETCH_EXHAUSTIVE = Yes
    DATASET = 0229Planregister
    ATTR_ACCUM_MODE = Merge Joined
    JOIN_KEYS = Dokumentid Dokumentid
    MSSQL_ADO_NAMED_CONNECTION = 0229Planregister
    MATCH_MULTIPLE_DISPLAY = Create a feature for each match
    ATTR_CONFLICT_RES = Use Original
    CACHE_SIZE = 5000
    TABLE = dbo.Dokument
    ADDED_FIELDS = Dokumentdato Dokumentnavn Dokumentstatus Dokumenttype
    MSSQL_ADO_COMMAND_TIMEOUT = 30
    MATCH_RULE_DISPLAY = Match All (1:M)
    MSSQL_ADO_QUERY_FEATURE_TYPES_FOR_MERGE_FILTERS = Yes
    FORMAT = MSSQL_ADO
    JOINED -> AttributeFilter
AttributeFilter
    ATTR_NAME = Dokumenttype
    ATTR_VALUES = 5,2,9,4,<MISSING>,<EMPTY>,<NULL>,<UNFILTERED>
    5 -> AttributeCreator
    2 -> Counter_3 [off]
    9 -> Counter_3
    4 -> Counter_3
    <UNFILTERED> -> Counter_3 [off]
Note: AttributeCreator [AttributeCreator] / Substitute Missing, Null and Empty by: No Substitution / Set 'filecopy_source_dataset' to '$(Bestemmelser)/@Value(Dokumentnavn)' / Set 'filecopy_dest_dataset' to '$(DestDataset_FILECOPY)' / Set 'filecopy_dest_filename' to '$(filecopy_dest_filename)_bestemmelser.pdf'
AttributeCreator
    ATTR_TABLE:
      SET_TO filecopy_source_dataset = $(Bestemmelser)/@Value(Dokumentnavn)
      SET_TO filecopy_dest_dataset = $(DestDataset_FILECOPY)
      SET_TO filecopy_dest_filename = $(filecopy_dest_filename)_bestemmelser.pdf
    -> filecopy (writer FILECOPY_1)
Counter_3
    DOMAIN = counter
    CNT_ATTR = _count
    START = 1
    SCOPE = Global
    -> AttributeCreator_3
AttributeCreator_3
    ATTR_TABLE:
      SET_TO filecopy_source_dataset = $(Andredok)/@Value(Dokumentnavn)
      SET_TO filecopy_dest_dataset = $(DestDataset_FILECOPY)
      SET_TO filecopy_dest_filename = $(filecopy_dest_filename)_@Value(_count).pdf
    -> filecopy (writer FILECOPY_1)
Note: Writer Type: File Copy / Feature Type: filecopy / Dataset: upload [FILECOPY] / Geometry: All / Attributes: / filecopy_source_dataset: char(512) / filecopy_dest_dataset: char(512) / filecopy_dest_filename: char(128)
filecopy (writer FILECOPY_1)
    attributes: filecopy_source_dataset char(512), filecopy_dest_dataset char(512), filecopy_dest_filename char(128)
