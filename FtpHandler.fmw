FME workspace FtpHandler.fmw
Title: FTPHandler
Description: Denne modell håndterer opplasting til ftp server.
På nåværende tidspunkt er stien til ftp-server hardkodet.
Requirements: FME 2016.1
History: 03.02.2017,Paal Pedersen,Oppdatert modellen til å laste opp xml til forside.

Parameters:
- Ordrenavn = 3455435.WI02290750.vg
- DestDataset_TEXTLINE = $(FME_MF_DIR)History\.txt   # Destination Text File
- STATUS =
- Ordrenummer =
- USER =   # Username
- PASS =   # Password
- SERVER =   # Server

Readers:
- PATH_1: PATH from $(FME_MF_DIR)ftp\upload

Writers:
- FILECOPY_1: FILECOPY to $(FME_MF_DIR)History\uploads
- TEXTLINE_1: TEXTLINE to $(DestDataset_TEXTLINE)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> Tester
Tester
    TEST_DESCRIPTION = ""
    BOOL_OP = OR
    TEST_MODE = Automatic
    TEST_CLAUSE = TEST @Value(path_type) = file
    PASSED -> Tester_2
    FAILED -> Tester_3
Tester_2
    TEST_DESCRIPTION = ""
    BOOL_OP = OR
    TEST_MODE = Automatic
    TEST_CLAUSE = TEST @Value(path_extension) BEGINS_WITH WI
    PASSED -> AttributeCreator
    FAILED -> AttributeCreator_2
AttributeCreator
    ATTR_TABLE:
      SET_TO path_filename = @Value(path_filename).pdf
      SET_TO path_extension = pdf
    -> AttributeCreator_2
AttributeCreator_2
    ATTR_TABLE:
      SET_TO filecopy_source_dataset = @Value(path_windows)
      SET_TO ftpcopy_dest_dataset = ftp://$(USER):$(PASS)@$(SERVER)/upload/
      SET_TO filecopy_dest_filename = @Value(path_filename)
      SET_TO filecopy_dest_dataset = $(FME_MF_DIR_ENCODED)History\uploads\$(Ordrenummer)\
    -> FTPCaller
Tester_3
    TEST_DESCRIPTION = ""
    BOOL_OP = AND
    TEST_MODE = Automatic
    TEST_CLAUSE:
      TEST @Value(path_rootname) = xml
      TEST @Value(path_type) = directory
    PASSED -> FeatureReader [INITIATOR]
FeatureReader
    FORMAT = PATH
    PATH_RETRIEVE_FILE_PROPERTIES = YES
    COMBINE_GEOM = Use Result
    PATH_GLOB_PATTERN = *
    PATH_TYPE = ANY
    ATTR_ACCUM_MODE = Only Use Result
    DATASET = @Value(path_windows)
    OUTPUT_FEATURES_DISPLAY = Schema and Data Features
    ATTRIBUTES = PATH,"path_unix,path_windows,path_rootname,path_filename,path_extension,path_filesize,path_ownername,path_readonly,path_modified_date,path_created_date,path_accessed_date,path_directory_unix,path_directory_windows,path_type,fme_geometry{0}"
    PATH -> TimeStamper
TimeStamper
    FMT = FME Date/Time (^Y^m^d^H^M^S)
    TIME_ATTR = _timestamp
    -> AttributeCreator_5
AttributeCreator_5
    ATTR_TABLE:
      SET_TO filecopy_source_dataset = @Value(path_windows)
      SET_TO ftpcopy_dest_dataset = ftp://$(USER):$(PASS)@$(SERVER)/upload/xml/
      SET_TO filecopy_dest_filename = @Value(path_filename)
      SET_TO filecopy_dest_dataset = $(FME_MF_DIR_ENCODED)History\uploads\$(Ordrenummer)\
    -> FTPCaller
FTPCaller
    ERROR_ATTR = _error
    UPLOAD_FILE = @Value(path_windows)
    VERIFY_SSL_CERTIFICATES = Yes
    TRANSFER_TYPE = Upload from a File
    MODE = Binary
    REMOTE_URL = @Value(ftpcopy_dest_dataset)@Value(filecopy_dest_filename)
    -> filecopy (writer FILECOPY_1)
    -> AttributeCreator_4
    <REJECTED> -> AttributeCreator_3
filecopy (writer FILECOPY_1)
AttributeCreator_4
    ATTR_TABLE = SET_TO text_line_data = Orderproduction was a $(STATUS). Successfully uploaded: $(Ordrenavn) to ftp://data.eiendomsinfo.no/orders
    -> text_line (writer TEXTLINE_1)
AttributeCreator_3
    ATTR_TABLE = SET_TO text_line_data = Orderproduction was a $(STATUS). Failed to upload: $(Ordrenavn) with filename: @Value(filecopy_dest_filename) to ftp://data.eiendomsinfo.no/orders
    -> text_line (writer TEXTLINE_1)
text_line (writer TEXTLINE_1)
    attributes: text_line_data buffer
