FME workspace Plandokumenter.fmw

Parameters:
- GNR = 118
- BNR = 102
- FNR = 0
- SNR = 0
- filecopy_dest_filename = Ordreid   # " " filecopy_dest_filename
- DestDataset_FILECOPY = $(FME_MF_DIR)ftp\upload   # Destination File Copy Folder
- Bestemmelser = X:\Data\planregister\0229\GjeldendeBestemmelser   # Sti til bestemmelser
- DestDataset_SPATIALITE = X:\Data\SQLITE\0229_UTVALG_EIENDOM.sl3   # Destination SpatiaLite Database File
- Vedtak = X:\Data\planregister\0229\VedtaksDokumenter   # Sti til Vedtak
- Andredok = X:\Data\planregister\0229\AndreDokumenter   # Sti til andre dokumenter

Writers:
- FILECOPY_1: FILECOPY to $(DestDataset_FILECOPY)

Creator
    NUM = 1
    GEOMTYPE = Geometry Object
    CREATED -> WorkspaceRunner
WorkspaceRunner
    WORKSPACE_FILE = $(FME_MF_DIR)UTVALG_EIENDOM.fmw
    WORKSPACE_PARAMETERS = GNR,$(GNR),BNR,$(BNR),FNR,$(FNR),SNR,$(SNR),DestDataset_SQLITE3,$(DestDataset_SPATIALITE)
    BLOCKING = Yes
    SUCCEEDED -> FeatureReader [INITIATOR]
FeatureReader
    COORDSYS = EPSG:25832
    INTERACT = <No Spatial Filter>
    OUTPUT_FEATURES_DISPLAY = Schema and Data Features
    FORMAT = SPATIALITE
    DATASET = $(DestDataset_SPATIALITE)
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    ATTR_ACCUM_MODE = Only Use Result
    SPATIALITE_QUERY_FEATURE_TYPES_FOR_MERGE_FILTERS = Yes
    COMBINE_GEOM = Use Result
    Teig -> Clipper [CLIPPER]
Creator_2
    NUM = 1
    GEOMTYPE = Geometry Object
    CREATED -> FeatureReader_2 [INITIATOR]
FeatureReader_2
    COORDSYS = EPSG:25832
    GDMMAPPERQUADRI_GDMR_USEFFSCACHE = yes
    GDMMAPPERQUADRI_GDMR_ADDGEOMETRYATTRIBUTES = no
    INTERACT = <No Spatial Filter>
    GDMMAPPERQUADRI_GDMR_ACCEPT2DPOINTSIN3DFEATURES = no
    OUTPUT_FEATURES_DISPLAY = Schema and Data Features
    GDMMAPPERQUADRI_GDMR_CHECKATTRIBTYPESACROSSFEATURES = no
    GDMMAPPERQUADRI_GDMR_MAXGAP = .2
    GDMMAPPERQUADRI_GDMR_CONVERTARCTOVECTORS = no
    FORMAT = GDMMAPPERQUADRI
    FEATURETYPES = RpOmråde
    GDMMAPPERQUADRI_GDMR_STOREOBJECTCODETOFME = no
    GDMMAPPERQUADRI_GDMR_READENVELOPE = NO
    DATASET = X:\Data\QUADRI\0229_RP3VN2.GDD
    GDMMAPPERQUADRI_GDMR_KEEPGEOMETRYONTEXTS = no
    GDMMAPPERQUADRI_GDMR_ADDTHEMECODE = no
    GDMMAPPERQUADRI_GDMR_ADDOBJTYPEATTRIBUTE = yes
    GDMMAPPERQUADRI_GDMR_USESSOSIATTRIBDEFS = no
    GDMMAPPERQUADRI_GDMR_STOREGDMSURFACEASFMEPOINT = no
    ATTRIBUTES = RbBevaringGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbBevaringOmråde,"FTEMA,FØRSTEDIGITALISERINGSDATO,GEOMETRITYPE,NASJONALAREALPLANID.KOMM,NASJONALAREALPLANID.PLANID,OBJTYPE,OPPDATERINGSDATO,PTEMA,REGFORM,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbFareOmråde,"FTEMA,FØRSTEDIGITALISERINGSDATO,GEOMETRITYPE,NASJONALAREALPLANID.KOMM,NASJONALAREALPLANID.PLANID,OBJTYPE,OPPDATERINGSDATO,REGFORM,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbFormålOmråde,"FELTNAVN,FTEMA,FØRSTEDIGITALISERINGSDATO,GEOMETRITYPE,NASJONALAREALPLANID.KOMM,NASJONALAREALPLANID.PLANID,OBJTYPE,OPPDATERINGSDATO,REGFORM,REGFORMUTDYP,UTNYTT.UTNTALL,UTNYTT.UTNTYP,VERTNIV,_CLOSED_BOUNDARY,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbRekkefølgeGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbRekkefølgeOmråde,"FTEMA,FØRSTEDIGITALISERINGSDATO,GEOMETRITYPE,NASJONALAREALPLANID.KOMM,NASJONALAREALPLANID.PLANID,OBJTYPE,OPPDATERINGSDATO,REGFORM,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbRestriksjonGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RbRestriksjonOmråde,"FELTNAVN,FTEMA,FØRSTEDIGITALISERINGSDATO,GEOMETRITYPE,NASJONALAREALPLANID.KOMM,NASJONALAREALPLANID.PLANID,OBJTYPE,OPPDATERINGSDATO,REGFORM,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpAngittHensynGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpAngittHensynSone,"FTEMA,FØRSTEDIGITALISERINGSDATO,GEOMETRITYPE,HENSYNSONENAVN,NASJONALAREALPLANID.KOMM,NASJONALAREALPLANID.PLANID,OBJTYPE,OPPDATERINGSDATO,RPANGITTHENSYN,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpArealformålOmråde,"BESKRIVELSE,EIERFORM,FELTNAVN,FTEMA,FØRSTEDIGITALISERINGSDATO,GEOMETRITYPE,NASJONALAREALPLANID.KOMM,NASJONALAREALPLANID.PLANID,OBJTYPE,OPPDATERINGSDATO,RPAREALFORMÅL,UTNYTT.UTNTALL,UTNYTT.UTNTYP,VERTNIV,_CLOSED_BOUNDARY,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpBestemmelseGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpBestemmelseOmråde,"BESTEMMELSEOMRNAVN,FTEMA,FØRSTEDIGITALISERINGSDATO,GEOMETRITYPE,NASJONALAREALPLANID.KOMM,NASJONALAREALPLANID.PLANID,OBJTYPE,OPPDATERINGSDATO,RPBESTEMMELSEHJEMMEL,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpBåndleggingGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpBåndleggingSone,"BÅNDLAGTFREMTIL,FTEMA,FØRSTEDIGITALISERINGSDATO,GEOMETRITYPE,HENSYNSONENAVN,NASJONALAREALPLANID.KOMM,NASJONALAREALPLANID.PLANID,OBJTYPE,OPPDATERINGSDATO,RPBÅNDLEGGING,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpFareGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpFareSone,"FTEMA,FØRSTEDIGITALISERINGSDATO,GEOMETRITYPE,HENSYNSONENAVN,NASJONALAREALPLANID.KOMM,NASJONALAREALPLANID.PLANID,OBJTYPE,OPPDATERINGSDATO,RPFARE,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpFormålGrense,"FØRSTEDIGITALISERINGSDATO,GEOMETRITYPE,KVALITET.MÅLEMETODE,KVALITET.NØYAKTIGHET,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpGrense,"FØRSTEDIGITALISERINGSDATO,GEOMETRITYPE,KVALITET.MÅLEMETODE,KVALITET.NØYAKTIGHET,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpJuridiskLinje,"FØRSTEDIGITALISERINGSDATO,GEOMETRITYPE,KVALITET.MÅLEMETODE,LTEMA,NASJONALAREALPLANID.KOMM,NASJONALAREALPLANID.PLANID,OBJTYPE,OPPDATERINGSDATO,RPJURLINJE,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpJuridiskPunkt,"FEATURE_ID,FØRSTEDIGITALISERINGSDATO,GEOMETRITYPE,KVALITET.MÅLEMETODE,NASJONALAREALPLANID.KOMM,NASJONALAREALPLANID.PLANID,OBJTYPE,OPPDATERINGSDATO,PTEMA,RPJURPUNKT,SYMBOL.DIM,SYMBOL.DREI,SYMBOL.FLYTT-N,SYMBOL.FLYTT-Ø,SYMBOL.STREK,VERTNIV,_original_geometry,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpOmråde,"FORSLAGSSTILLERTYPE,FTEMA,FØRSTEDIGITALISERINGSDATO,GEOMETRITYPE,IKRAFT,KUNNGJØRINGSDATO,LINK{0}.LINK,LINK{1}.LINK,LINK{2}.LINK,LOVREFBESKRIVELSE,LOVREFERANSE,NASJONALAREALPLANID.KOMM,NASJONALAREALPLANID.PLANID,OBJTYPE,OPPDATERINGSDATO,PLANBEST,PLANNAVN,PLANSTAT,PLANTYPE,PTEMA,VERTNIV,_CLOSED_BOUNDARY,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpPåskrift,"FEATURE_ID,FØRSTEDIGITALISERINGSDATO,GEOMETRITYPE,KVALITET.MÅLEMETODE,KVALITET.NØYAKTIGHET,NASJONALAREALPLANID.KOMM,NASJONALAREALPLANID.PLANID,OBJTYPE,OPPDATERINGSDATO,RPPÅSKRIFTTYPE,TEKST.FØLGER-LINJE,TEKST.RETNING-NORD,TEKST.RETNING-ØST,TEKST.START-NORD,TEKST.START-ØST,TEKST.STRENG,TTEMA,VERTNIV,_original_geometry,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpRegulertHøyde,"GEOMETRITYPE,HØYDEFRAPLANBEST.HØYDE-REF,HØYDEFRAPLANBEST.REGULERTHØYDE,KVALITET.MÅLEMETODE,LTEMA,NASJONALAREALPLANID.KOMM,NASJONALAREALPLANID.PLANID,OBJTYPE,OPPDATERINGSDATO,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpSikringGrense,"FØRSTEDIGITALISERINGSDATO,GEOMETRITYPE,KVALITET.MÅLEMETODE,LTEMA,OBJTYPE,OPPDATERINGSDATO,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}",RpSikringSone,"FTEMA,FØRSTEDIGITALISERINGSDATO,GEOMETRITYPE,HENSYNSONENAVN,NASJONALAREALPLANID.KOMM,NASJONALAREALPLANID.PLANID,OBJTYPE,OPPDATERINGSDATO,RPSIKRING,VERTNIV,fme_geomattr{3}.fme_text_string,fme_geometry{0},fme_geometry{10},fme_geometry{11},fme_geometry{12},fme_geometry{13},fme_geometry{14},fme_geometry{1},fme_geometry{2},fme_geometry{3},fme_geometry{4},fme_geometry{5},fme_geometry{6},fme_geometry{7},fme_geometry{8},fme_geometry{9}"
    GDMMAPPERQUADRI_GDMR_ADDFMETEXTS = no
    GDMMAPPERQUADRI_GDMR_READTOPOLOGY = no
    GDMMAPPERQUADRI_GDMR_ONEFEATURETYPEONLY = NO
    GDMMAPPERQUADRI_GDMR_CLIPTOENVELOPE = yes
    GDMMAPPERQUADRI_GDMR_VERSION = 411
    ATTR_ACCUM_MODE = Only Use Result
    GDMMAPPERQUADRI_GDMR_CONVERTPOINTATTRIBSTOPOINTS = no
    GDMMAPPERQUADRI_GDMR_LISTATTRIBSASFMELISTS = 3
    COMBINE_GEOM = Use Result
    RpOmråde -> Clipper [CLIPPEE]
Clipper
    CLIP_TYPE = Multiple Clippers
    CREATE_AGGREGATES = Yes
    BOUNDARY_CASES = Treat as Inside
    PRESERVE_CLIPPEE_EXTENTS = No
    ATTR_CONFLICT_RES = Use Clippee
    CONNECT_Z_MODE = First Wins
    CLIPPED_ATTR = _clipped
    ATTR_ACCUM_MODE = Merge Clipper
    LINES_AS_SEGMENTS = No
    INSIDE -> DuplicateFilter
DuplicateFilter
    KEYATTR = NASJONALAREALPLANID.PLANID
    INPUT_ORDERED_CHOICE = No
    UNIQUE -> Joiner_2
Joiner_2
    MSSQL_ADO_NAMED_CONNECTION = 0229Planregister
    MATCH_MULTIPLE_DISPLAY = Create a feature for each match
    MSSQL_ADO_QUERY_FEATURE_TYPES_FOR_MERGE_FILTERS = Yes
    ATTR_CONFLICT_RES = Use Original
    ATTR_ACCUM_MODE = Merge Joined
    DATASET = 0229Planregister
    MATCH_RULE_DISPLAY = Match All (1:M)
    FORMAT = MSSQL_ADO
    ADDED_FIELDS = PlanBestemmelser PlanType
    PREFETCH_EXHAUSTIVE = Yes
    CACHE_SIZE = 5000
    JOIN_KEYS = NASJONALAREALPLANID.PLANID Planid
    MSSQL_ADO_COMMAND_TIMEOUT = 30
    TABLE = dbo.Arealplan
    JOINED -> Joiner
Joiner
    MSSQL_ADO_NAMED_CONNECTION = 0229Planregister
    MATCH_MULTIPLE_DISPLAY = Create a feature for each match
    MSSQL_ADO_QUERY_FEATURE_TYPES_FOR_MERGE_FILTERS = Yes
    ATTR_CONFLICT_RES = Use Original
    ATTR_ACCUM_MODE = Merge Joined
    DATASET = 0229Planregister
    MATCH_RULE_DISPLAY = Match All (1:M)
    FORMAT = MSSQL_ADO
    ADDED_FIELDS = DokPlanId Dokumentid
    PREFETCH_EXHAUSTIVE = Yes
    CACHE_SIZE = 5000
    JOIN_KEYS = NASJONALAREALPLANID.PLANID Planid
    MSSQL_ADO_COMMAND_TIMEOUT = 30
    TABLE = dbo.DokumenterPlan
    JOINED -> Joiner_3
Joiner_3
    MSSQL_ADO_NAMED_CONNECTION = 0229Planregister
    MATCH_MULTIPLE_DISPLAY = Create a feature for each match
    MSSQL_ADO_QUERY_FEATURE_TYPES_FOR_MERGE_FILTERS = Yes
    ATTR_CONFLICT_RES = Use Original
    ATTR_ACCUM_MODE = Merge Joined
    DATASET = 0229Planregister
    MATCH_RULE_DISPLAY = Match All (1:M)
    FORMAT = MSSQL_ADO
    ADDED_FIELDS = Dokumentdato Dokumentnavn Dokumentstatus Dokumenttype
    PREFETCH_EXHAUSTIVE = Yes
    CACHE_SIZE = 5000
    JOIN_KEYS = Dokumentid Dokumentid
    MSSQL_ADO_COMMAND_TIMEOUT = 30
    TABLE = dbo.Dokument
    JOINED -> AttributeFilter
AttributeFilter
    ATTR_NAME = Dokumenttype
    ATTR_VALUES = 5,2,9,4,<MISSING>,<EMPTY>,<NULL>,<UNFILTERED>
    5 -> Tester
    2 -> Tester_2
    9 -> Counter_3
    4 -> Counter_3
Tester
    TEST_CLAUSE:
      TEST @Value(Dokumenttype) = 5
      TEST @Value(Dokumentstatus) = 2
    BOOL_OP = AND
    TEST_DESCRIPTION = ""
    TEST_MODE = Automatic
    PASSED -> Counter
Counter
    START = 1
    CNT_ATTR = _count
    SCOPE = Global
    DOMAIN = counter
    -> AttributeCreator
Note: AttributeCreator [AttributeCreator] / Substitute Missing, Null and Empty by: No Substitution / Set 'filecopy_source_dataset' to '$(Bestemmelser)/@Value(Dokumentnavn)' / Set 'filecopy_dest_dataset' to '$(DestDataset_FILECOPY)' / Set 'filecopy_dest_filename' to '$(filecopy_dest_filename)_@Value(_count).pdf'
AttributeCreator
    ATTR_TABLE:
      SET_TO filecopy_source_dataset = $(Bestemmelser)/@Value(Dokumentnavn)
      SET_TO filecopy_dest_dataset = $(DestDataset_FILECOPY)
      SET_TO filecopy_dest_filename = $(filecopy_dest_filename)_@Value(_count).pdf
    -> filecopy (writer FILECOPY_1)
Tester_2
    TEST_CLAUSE:
      TEST @Value(Dokumenttype) = 2
      TEST @Value(Dokumentstatus) = 2
    BOOL_OP = AND
    TEST_DESCRIPTION = ""
    TEST_MODE = Automatic
    PASSED -> Counter_2
Counter_2
    START = 1
    CNT_ATTR = _count
    SCOPE = Global
    DOMAIN = counter
    -> AttributeCreator_2
AttributeCreator_2
    ATTR_TABLE:
      SET_TO filecopy_source_dataset = $(Vedtak)/@Value(Dokumentnavn)
      SET_TO filecopy_dest_dataset = $(DestDataset_FILECOPY)
      SET_TO filecopy_dest_filename = $(filecopy_dest_filename)_@Value(_count).pdf
    -> filecopy (writer FILECOPY_1)
Counter_3
    START = 1
    CNT_ATTR = _count
    SCOPE = Global
    DOMAIN = counter
    -> AttributeCreator_3
AttributeCreator_3
    ATTR_TABLE:
      SET_TO filecopy_source_dataset = $(Andredok)/@Value(Dokumentnavn)
      SET_TO filecopy_dest_dataset = $(DestDataset_FILECOPY)
      SET_TO filecopy_dest_filename = $(filecopy_dest_filename)_@Value(_count).pdf
    -> filecopy (writer FILECOPY_1)
Note: Writer Type: File Copy / Feature Type: filecopy / Dataset: upload [FILECOPY] / Geometry: All / Attributes: / filecopy_source_dataset: char(512) / filecopy_dest_dataset: char(512) / filecopy_dest_filename: char(128)
filecopy (writer FILECOPY_1)
    attributes: filecopy_source_dataset char(512), filecopy_dest_dataset char(512), filecopy_dest_filename char(128)
