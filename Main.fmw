FME workspace Main.fmw

Parameters:
- Server =   # Ftp server
- Brukernavn =   # bruker
- password =
- path_orders = $(FME_MF_DIR)orders   # Path to orders
- Ordrenavn:   # Python Script
      from ftplib import FTP
      import os,re
      ftp = FTP(FME_MacroValues['Server'])
      ftp.login(FME_MacroValues['Brukernavn'], FME_MacroValues['password'], 'AUTH TLS')
      ftp.cwd('orders')
      
      path = FME_MacroValues['path_orders']
      if re.search('\$\(',path):
          _path = path.split('(')[1].split(')')[0]
          _path_rest = path.split(')')[1]
      path = os.path.join(FME_MacroValues[_path],_path_rest).replace('/','\\')
      
      if not ftp.nlst():
          raise Exception("There are no orders!")
      else:
          f=open(os.path.join(path,ftp.nlst()[0]),'w')
          ftp.retrbinary('RETR %s' % ftp.nlst()[0], lambda data: f.write(data))
          f.close()
          return '.'.join(ftp.nlst()[0].split('.')[0:2])
      ftp.close()
      return 0
- _gnr:   # Python Script
      from ftplib import FTP
      import os,re
      ftp = FTP(FME_MacroValues['Server'])
      ftp.login(FME_MacroValues['Brukernavn'], FME_MacroValues['password'], 'AUTH TLS')
      ftp.cwd('orders')
      def get_num(x):
          return int(''.join(ele for ele in x if ele.isdigit()))
      _nr=0
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^gnr', line):
              _nr=get_num(line)
      f.close()
      return _nr
- _bnr:   # Python Script
      from ftplib import FTP
      import os,re
      ftp = FTP(FME_MacroValues['Server'])
      ftp.login(FME_MacroValues['Brukernavn'], FME_MacroValues['password'], 'AUTH TLS')
      ftp.cwd('orders')
      def get_num(x):
          return int(''.join(ele for ele in x if ele.isdigit()))
      _nr=0
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^bnr', line):
              _nr=get_num(line)
      f.close()
      return _nr
- _fnr:   # Python Script
      from ftplib import FTP
      import os,re
      ftp = FTP(FME_MacroValues['Server'])
      ftp.login(FME_MacroValues['Brukernavn'], FME_MacroValues['password'], 'AUTH TLS')
      ftp.cwd('orders')
      def get_num(x):
          return int(''.join(ele for ele in x if ele.isdigit()))
      _nr=0
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^fnr', line):
              _nr=get_num(line)
      f.close()
      return _nr
- _snr:   # Python Script
      from ftplib import FTP
      import os,re
      ftp = FTP(FME_MacroValues['Server'])
      ftp.login(FME_MacroValues['Brukernavn'], FME_MacroValues['password'], 'AUTH TLS')
      ftp.cwd('orders')
      def get_num(x):
          return int(''.join(ele for ele in x if ele.isdigit()))
      _nr=0
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^snr', line):
              _nr=get_num(line)
      f.close()
      return _nr
- _ref:   # Python Script
      from ftplib import FTP
      import os,re
      ftp = FTP(FME_MacroValues['Server'])
      ftp.login(FME_MacroValues['Brukernavn'], FME_MacroValues['password'], 'AUTH TLS')
      ftp.cwd('orders')
      
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^ref',line):
              _ref = line.split('=')[1].split('&')[0]
      f.close()
      return _ref
- adresse:   # Python Script
      from ftplib import FTP
      import os,re
      ftp = FTP(FME_MacroValues['Server'])
      ftp.login(FME_MacroValues['Brukernavn'], FME_MacroValues['password'], 'AUTH TLS')
      ftp.cwd('orders')
      
      path = FME_MacroValues['path_orders']
      if re.search('\$\(',path):
          _path = path.split('(')[1].split(')')[0]
          _path_rest = path.split(')')[1]
      path = os.path.join(FME_MacroValues[_path],_path_rest).replace('/','\\')
      
      f=open(os.path.join(path,ftp.nlst()[0]),'r')
      for line in f.readlines():
          if re.match(r'^adresse',line):
              if re.search('\$',line):
                  _adresse = line.split('$')[1].split('&')[0]
              else:
                  _adresse = line.split('=')[1].split('&')[0]
      f.close()
      print _adresse
      
      if _adresse == '{xml.adresse}':
          return
      else:
          try:
              return _adresse.split(',')[0]
          except ValueError:
              return

Note: Håndter hvilke jobber som skal kjøres
WorkspaceHandler
    __SNR = @Value(__snr)
    _ADRESSE = @Value(_adresse)
    __BNR = @Value(__bnr)
    Ordrenavn = $(Ordrenavn)
    _NAMELIST_1_ = @Value(_namelist{1})
    _REFERANSE = @Value(_Referanse)
    __FNR = @Value(__fnr)
    __GNR = @Value(__gnr)
    Succeeded -> WorkspaceRunner_2
    Failed -> WorkspaceRunner_3
Note: Laster opp data til ftp
WorkspaceRunner_2
    WORKSPACE_PARAMETERS = Ordrenavn,$(Ordrenavn).vg,DestDataset_TEXTLINE,$(FME_MF_DIR_USERTYPED)History\$(Ordrenavn)_upload.txt,STATUS,@Value(STATUS),Ordrenummer,@Value(_namelist{0}),USER,@Value(_Brukernavn),PASS,@Value(_password),SERVER,@Value(_Server)
    BLOCKING = Yes
    WORKSPACE_FILE = $(FME_MF_DIR)FtpHandler.fmw
    SUCCEEDED -> WorkspaceRunner_3
    FAILED -> Emailer_2
Note: Slett ordren fra ftp
WorkspaceRunner_3
    WORKSPACE_PARAMETERS = Ordrenavn,$(Ordrenavn).vg,DestDataset_TEXTLINE,$(FME_MF_DIR_USERTYPED)History\$(Ordrenavn)_delete.txt,STATUS,@Value(STATUS),USER,@Value(_Brukernavn),PASS,@Value(_password),SERVER,@Value(_Server)
    BLOCKING = Yes
    WORKSPACE_FILE = $(FME_MF_DIR)FtpDelete.fmw
    SUCCEEDED -> WorkspaceRunner
    FAILED -> Emailer_2
Note: Starter en ny instans av MAIN workspace.
WorkspaceRunner
    BLOCKING = Yes
    WORKSPACE_FILE = $(FME_MF_DIR)Main.fmw
    FAILED -> Emailer_2
Note: Send en melding til / modellansvarlig ved avvik.
Emailer_2
    PASSWORD =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
    BODY = Se vedlagt loggfil for ordre: @Value(_Ordrenavn)
    FROM = paal.pedersen@enebakk.kommune.no
    TO = paal.pedersen@enebakk.kommune.no
    BODYTYPE = Plain Text
    HOST = exchange.ansatt.oikt.net
    PORT = 25
    AUTHENTICATION = YES
    SUBJECT = Status ordre
    ENCRYPTION = None
    TIMEOUT = 5
    CCGROUP = No
    USERNAME = paaped

Bookmark: Data fra ftp
Note: Parametre hentes fra private paramters, som igjen henter data i fra ftp. Ordre lastes ned og leses via de private parameterene. Dataene lagres i dette tilfelle på V:\FME\Ambitia
Creator
    GEOMTYPE = Geometry Object
    NUM = 1
    CREATED -> ParameterFetcher
ParameterFetcher
    ATTR_LIST = __bnr {$(_bnr)} __fnr {$(_fnr)} __gnr {$(_gnr)} __snr {$(_snr)} _Ordrenavn {$(Ordrenavn)} _Referanse {$(_ref)} _adresse {$(adresse)} _Brukernavn {$(Brukernavn)} _password {$(password)} _Server {$(Server)}
    -> AttributeSplitter
AttributeSplitter
    DELIMITER = .
    DROP_EMPTY_PARTS = No
    TRIM_OPTION = Both
    LIST_NAME = _namelist
    ATTR_NAME = _Ordrenavn
    -> WorkspaceHandler

FME custom transformer WI02291360

Parameters:
- Ordrenavn =
- __SNR = @Value(__snr)   # Snr
- __GNR = @Value(__gnr)   # Gnr
- __BNR = @Value(__bnr)   # Bnr
- __FNR = @Value(__fnr)   # Fnr

Input (input)
    -> UtvalgEiendomKart
    -> WorkspaceRunner_12
    -> WorkspaceRunner_13
UtvalgEiendomKart
    __SNR = @Value(__snr)
    __BNR = @Value(__bnr)
    SourceDataset_SQLITE3 = X:\Data\SQLITE\0229_EIENDOM_BOX.SL3
    __FNR = @Value(__fnr)
    __GNR = @Value(__gnr)
    -> WorkspaceRunner_15
WorkspaceRunner_15
    WORKSPACE_PARAMETERS = filename,$(Ordrenavn)_kart,_gnr,@Value(__gnr),_bnr,@Value(__bnr),_fnr,@Value(__fnr),_snr,@Value(__snr),A4,YES
    BLOCKING = Yes
    WORKSPACE_FILE = $(FME_MF_DIR)Komplan.fmw
    SUCCEEDED -> Succeeded (output)
    FAILED -> Counter
WorkspaceRunner_12
    WORKSPACE_PARAMETERS = GNR,@Value(__gnr),BNR,@Value(__bnr),FNR,@Value(__fnr),SNR,@Value(__snr),filecopy_dest_filename,$(Ordrenavn)
    BLOCKING = Yes
    WORKSPACE_FILE = $(FME_MF_DIR)WI02291360_dokumenter.fmw
    SUCCEEDED -> Succeeded (output)
    FAILED -> Counter
WorkspaceRunner_13
    WORKSPACE_PARAMETERS = GNR,@Value(__gnr),BNR,@Value(__bnr),FNR,@Value(__fnr),SNR,@Value(__snr),Ordrenavn,$(Ordrenavn)
    BLOCKING = Yes
    WORKSPACE_FILE = $(FME_MF_DIR)Kommuneplan_analyse.fmw
    SUCCEEDED -> Succeeded (output)
    FAILED -> Counter
Succeeded (output)
Counter
    CNT_ATTR = W1360
    START = 1
    SCOPE = Global
    DOMAIN = W1360
    -> Tester
Tester
    TEST_DESCRIPTION = ""
    BOOL_OP = OR
    TEST_MODE = Automatic
    TEST_CLAUSE = TEST @Value(W1360) = 3
    PASSED -> Failed (output)
Failed (output)

FME custom transformer WI02291350

Parameters:
- Ordrenavn =
- __SNR = @Value(__snr)   # Snr
- __GNR = @Value(__gnr)   # Gnr
- __BNR = @Value(__bnr)   # Bnr
- __FNR = @Value(__fnr)   # Fnr

Input (input)
    -> UtvalgEiendomKart
    -> WorkspaceRunner_9
    -> WorkspaceRunner_11
UtvalgEiendomKart
    __SNR = @Value(__snr)
    __BNR = @Value(__bnr)
    SourceDataset_SQLITE3 = X:\Data\SQLITE\0229_EIENDOM_BOX.SL3
    __FNR = @Value(__fnr)
    __GNR = @Value(__gnr)
    -> WorkspaceRunner_14
WorkspaceRunner_14
    WORKSPACE_PARAMETERS = filename,$(Ordrenavn),DestDataset_PDF2D,$(FME_MF_DIR_ENCODED)ftp\upload\$(Ordrenavn).pdf,_gnr,@Value(__gnr),_bnr,@Value(__bnr),_fnr,@Value(__fnr),_snr,@Value(__snr),A4,YES
    BLOCKING = Yes
    WORKSPACE_FILE = $(FME_MF_DIR)Detaljplan_3.fmw
    SUCCEEDED -> Succeeded (output)
    FAILED -> Counter
WorkspaceRunner_9
    WORKSPACE_PARAMETERS = GNR,@Value(__gnr),BNR,@Value(__bnr),FNR,@Value(__fnr),SNR,@Value(__snr),filecopy_dest_filename,$(Ordrenavn)
    BLOCKING = Yes
    WORKSPACE_FILE = $(FME_MF_DIR)Plandokumenter.fmw
    SUCCEEDED -> Succeeded (output)
    FAILED -> Counter
WorkspaceRunner_11
    WORKSPACE_PARAMETERS = GNR,@Value(__gnr),BNR,@Value(__bnr),FNR,@Value(__fnr),SNR,@Value(__snr),Ordrenavn,$(Ordrenavn)
    BLOCKING = Yes
    WORKSPACE_FILE = $(FME_MF_DIR)Regplan_analyse.fmw
    SUCCEEDED -> Succeeded (output)
    FAILED -> Counter
Succeeded (output)
Counter
    CNT_ATTR = W1350
    START = 1
    SCOPE = Global
    DOMAIN = W1350
    -> Tester
Tester
    TEST_DESCRIPTION = ""
    BOOL_OP = OR
    TEST_MODE = Automatic
    TEST_CLAUSE = TEST @Value(W1350) = 3
    PASSED -> Failed (output)
Failed (output)

FME custom transformer WorkspaceHandler

Parameters:
- __BNR = @Value(__bnr)   # Bnr
- _NAMELIST_1_ = @Value(_namelist{1})   # Namelist{1}
- __FNR = @Value(__fnr)   # Fnr
- __GNR = @Value(__gnr)   # Gnr
- __SNR = @Value(__snr)   # Snr
- Ordrenavn =
- _REFERANSE = @Value(_Referanse)   # Referanse
- _ADRESSE = @Value(_adresse)   # Adresse

Input (input)
    -> ParameterFetcher
ParameterFetcher
    ATTR_LIST = _Ordrenavn {$(Ordrenavn)}
    -> AttributeSplitter
AttributeSplitter
    DELIMITER = .
    DROP_EMPTY_PARTS = No
    TRIM_OPTION = Both
    LIST_NAME = _list
    ATTR_NAME = _Ordrenavn
    -> AttributeCreator_3
AttributeCreator_3
    ATTR_TABLE = SET_TO OrderId = @Value(_list{0})
    -> AttributeFilter
Note: WI02290109 = Grunnkart / WI02290510 = Ledningskart / WI02291600 = Ortofoto / WI02290750 = Måebrev/SB / WI02297112 = Kommunaleavgifter / WI02297104 = Ferdigattest/MB / WI02297113 = Restanser/Legalpant / WI02290900 = Bygningstegninger / WI02297116 = Gjeldendeplanstatus / WI02291350 = Reguleringsplan + dok / WI02291360 = Kommuneplan + dok / WI02297108 = Vei, Vann og Avløpsforhold
AttributeFilter
    ATTR_VALUES = WI02290109,WI02290510,WI02291600,WI02290750,WI02297112,WI02297104,WI02297113,WI02290900,WI02297116,WI02291350,WI02291360,WI02297108,<EMPTY>,WI0229,<MISSING>,<NULL>,<UNFILTERED>
    ATTR_NAME = _namelist{1}
    WI02290109 -> WorkspaceRunner_2
    WI02290510 -> WorkspaceRunner
    WI02291600 -> WorkspaceRunner_3
    WI02290750 -> WorkspaceRunner_7
    WI02297112 -> WI02297112 [WorkspaceRunner_6_Input]
    WI02297104 -> WI02297104
    WI02290900 -> WorkspaceRunner_5
    WI02291350 -> WI02291350
    WI02291360 -> WI02291360
    WI02297108 -> WorkspaceRunner_8
    WI0229 -> Situasjonskart
WorkspaceRunner_2
    WORKSPACE_PARAMETERS = filename,$(Ordrenavn),DestDataset_PDF2D,$(FME_MF_DIR_USERTYPED)ftp\upload\$(Ordrenavn).pdf,_gnr,@Value(__gnr),_bnr,@Value(__bnr),_fnr,@Value(__fnr),_snr,@Value(__snr),A4,YES
    BLOCKING = Yes
    WORKSPACE_FILE = $(FME_MF_DIR)Grunnkart_v3.fmw
    SUCCEEDED -> FeatureHolder
    FAILED -> FeatureHolder_2
WorkspaceRunner
    WORKSPACE_PARAMETERS = DestDataset_PDF2D,$(FME_MF_DIR_ENCODED)ftp\upload\$(Ordrenavn).pdf,_gnr,@Value(__gnr),_bnr,@Value(__bnr),_fnr,@Value(__fnr),_snr,@Value(__snr),A4,YES
    BLOCKING = Yes
    WORKSPACE_FILE = $(FME_MF_DIR)Ledningskart_v3.fmw
    SUCCEEDED -> FeatureHolder
    FAILED -> FeatureHolder_2
WorkspaceRunner_3
    WORKSPACE_PARAMETERS = filename,$(Ordrenavn),DestDataset_PDF2D,$(FME_MF_DIR_USERTYPED)ftp\upload\$(Ordrenavn).pdf,_gnr,@Value(__gnr),_bnr,@Value(__bnr),_fnr,@Value(__fnr),_snr,@Value(__snr),A4,YES
    BLOCKING = Yes
    WORKSPACE_FILE = $(FME_MF_DIR)Flyfoto_3.fmw
    SUCCEEDED -> FeatureHolder
    FAILED -> FeatureHolder_2
WorkspaceRunner_7
    WORKSPACE_PARAMETERS = SourceDataset_PATH,X:\Data\Webdokumenter\Maalebrev\0229,gnr,@Value(__gnr),bnr,@Value(__bnr),DestDataset_FILECOPY,$(FME_MF_DIR_USERTYPED)ftp\upload,Filname,$(Ordrenavn)
    BLOCKING = Yes
    WORKSPACE_FILE = $(FME_MF_DIR)Målebrev.fmw
    SUCCEEDED -> FeatureHolder
    FAILED -> FeatureHolder_2
WI02297112
    __SNR = @Value(__snr)
    ORDERID = @Value(OrderId)
    __BNR = @Value(__bnr)
    _ORDRENAVN = @Value(_Ordrenavn)
    _REFERANSE = @Value(_Referanse)
    __FNR = @Value(__fnr)
    __GNR = @Value(__gnr)
    WorkspaceRunner_4_Succeeded -> FeatureHolder
    WorkspaceRunner_4_Failed -> FeatureHolder_2
WI02297104
    Ordrenavn = @Value(_Ordrenavn)
    __BNR = @Value(__bnr)
    __GNR = @Value(__gnr)
    WorkspaceRunner_10_Succeeded -> FeatureHolder
    WorkspaceRunner_6_Failed -> FeatureHolder_2
WorkspaceRunner_5
    WORKSPACE_PARAMETERS = gnr,@Value(__gnr),bnr,@Value(__bnr),Ordrenavn,$(Ordrenavn)
    BLOCKING = Yes
    WORKSPACE_FILE = $(FME_MF_DIR)Plantegninger.fmw
    SUCCEEDED -> FeatureHolder
    FAILED -> FeatureHolder_2
WI02291350
    __SNR = @Value(__snr)
    Ordrenavn = @Value(_Ordrenavn)
    __BNR = @Value(__bnr)
    __FNR = @Value(__fnr)
    __GNR = @Value(__gnr)
    Succeeded -> FeatureHolder
    Failed -> FeatureHolder_2
WI02291360
    __SNR = @Value(__snr)
    Ordrenavn = @Value(_Ordrenavn)
    __BNR = @Value(__bnr)
    __FNR = @Value(__fnr)
    __GNR = @Value(__gnr)
    Succeeded -> FeatureHolder
    Failed -> FeatureHolder_2
WorkspaceRunner_8
    WORKSPACE_PARAMETERS = GNR,@Value(__gnr),BNR,@Value(__bnr),FNR,@Value(__fnr),SNR,@Value(__snr),msdocfile,$(FME_MF_DIR_USERTYPED)ftp\upload\$(Ordrenavn).docx
    BLOCKING = No
    WORKSPACE_FILE = $(FME_MF_DIR)Vegforhold.fmw
    SUCCEEDED -> FeatureHolder
    FAILED -> FeatureHolder_2
Situasjonskart
    __SNR = @Value(__snr)
    _ADRESSE = @Value(_adresse)
    Ordrenavn = @Value(_Ordrenavn)
    __BNR = @Value(__bnr)
    __FNR = @Value(__fnr)
    __GNR = @Value(__gnr)
    Succeeded -> FeatureHolder
    Failed -> FeatureHolder_2
Note: Alle successfulle ordre sendes hit
FeatureHolder
    -> AttributeCreator
AttributeCreator
    ATTR_TABLE = SET_TO STATUS = SUCCESSFUL
    -> Succeeded (output)
Succeeded (output)
Note: Alle unsuccessfulle ordre sendes hit
FeatureHolder_2
    -> AttributeCreator_2
AttributeCreator_2
    ATTR_TABLE = SET_TO STATUS = UNSUCCESSFUL
    -> Failed (output)
Failed (output)

FME custom transformer UtvalgEiendomKart

Parameters:
- __FNR = @Value(__fnr)   # __fnr
- __SNR = @Value(__snr)   # __snr
- __GNR = @Value(__gnr)   # __gnr
- __BNR = @Value(__bnr)   # __bnr
- SourceDataset_SQLITE3 = X:\Data\SQLITE\0229_EIENDOM_BOX.SL3   # Source SQLite Database File(s)

Input (input)
    -> AttributeCreator
Note: AttributeCreator [AttributeCreator] / Substitute Missing, Null and Empty by: No Substitution / Set 'WHERECLAUSE' to 'GNR =@Value(__gnr) AND BNR = @Value(__bnr) AND FNR = @Value(__fnr) AND SNR = @Value(__snr)'
Note: Vi lager en SQL spørring som skal gjøre det sjappt å / hente data fra SQLite basen, som så leses som en / spatialite base for høyere performance.
AttributeCreator
    ATTR_TABLE = SET_TO WHERECLAUSE = GNR =@Value(__gnr) AND BNR = @Value(__bnr) AND FNR = @Value(__fnr) AND SNR = @Value(__snr)
    -> FeatureReader [INITIATOR]
    -> Tester
Sorter
    SORT_PARM = rekkefølge NUMERIC ASCENDING
    SORTED -> Sampler
Note: Vi trenger kun én teig
Sampler
    SAMPLE_MODE = No
    RATE = 1
    SAMPLE_TYPE_LONG = First N Features
    SAMPLED -> Output (output)
Output (output)

Bookmark: Les data fra spatialite
Note: FeatureReader [FeatureReader] / Format: SPATIALITE / Dataset: $(SourceDataset_SQLITE3) / Feature Types to Read: Teig / WHERE Clause: @Value(WHERECLAUSE) / Spatial Interaction: <No Spatial Filter> / Maximum Features to Read: <not set> / Attribute Accumulation Mode: Only Use Result / Geometry Handling: Use Result / Exposed Attributes: <not set> / Caching Enabled: NO / Features To Output: Schema and Data Features
FeatureReader
    SPATIALITE_QUERY_FEATURE_TYPES_FOR_MERGE_FILTERS = Yes
    WHERE = @Value(WHERECLAUSE)
    COMBINE_GEOM = Use Result
    INTERACT = <No Spatial Filter>
    ATTR_ACCUM_MODE = Only Use Result
    FORMAT = SPATIALITE
    FEATURETYPES = Teig
    ATTRIBUTES = Teig,"GNR,BNR,FNR,SNR,HOVEDTEIG,_xmax,_xmin,_ymax,_ymin,_zmax,_zmin"
    OUTPUT_FEATURES_DISPLAY = Schema and Data Features
    DATASET = $(SourceDataset_SQLITE3)
    Teig -> AttributeCreator_3
    INITIATOR -> FeatureMerger [REQUESTOR]
Tester
    TEST_DESCRIPTION = ""
    BOOL_OP = OR
    TEST_MODE = Automatic
    TEST_CLAUSE = TEST @Value(__snr) != 0
    PASSED -> AttributeCreator_5
AttributeCreator_5
    ATTR_TABLE:
      SET_TO WHERECLAUSE = GNR =@Value(__gnr) AND BNR = @Value(__bnr) AND FNR = @Value(__fnr) AND SNR = 0
      SET_TO __snr = 0
    -> FeatureReader_2 [INITIATOR]
Note: Vi setter opp 2 featurereadere i tilfelle orderen / inneholder et seksjonsnr der det ikke finnes en / tilsvarene eindomsteig med seksjonsnr.
FeatureReader_2
    SPATIALITE_QUERY_FEATURE_TYPES_FOR_MERGE_FILTERS = Yes
    WHERE = @Value(WHERECLAUSE)
    COMBINE_GEOM = Use Result
    INTERACT = <No Spatial Filter>
    ATTR_ACCUM_MODE = Only Use Result
    FORMAT = SPATIALITE
    FEATURETYPES = Teig
    ATTRIBUTES = Teig,"GNR,BNR,FNR,SNR,HOVEDTEIG,_xmax,_xmin,_ymax,_ymin,_zmax,_zmin"
    OUTPUT_FEATURES_DISPLAY = Schema and Data Features
    DATASET = $(SourceDataset_SQLITE3)
    Teig -> AttributeCreator_4
    INITIATOR -> FeatureMerger_2 [REQUESTOR]

Bookmark: Lag en egenskap som setter en rekkefølge i tilfelle vi vår treff på begge.
AttributeCreator_3
    ATTR_TABLE = SET_TO rekkefølge = 1
    -> FeatureMerger [SUPPLIER]
AttributeCreator_4
    ATTR_TABLE = SET_TO rekkefølge = 2
    -> FeatureMerger_2 [SUPPLIER]

Bookmark: Koble samme for å få med egenskapene fra de publiserte parametre
FeatureMerger
    REJECT_NULL_MISSING_KEYS = No
    ATTR_ACCUM_MODE = Merge Supplier
    PROCESS_DUPS = No
    SUPPLIERS_FIRST = No
    JOIN_KEYS = @Value(__gnr) @Value(GNR) AUTO @Value(__bnr) @Value(BNR) AUTO @Value(__fnr) @Value(FNR) AUTO @Value(__snr) @Value(SNR) AUTO
    MERGE_TYPE = Attributes Only
    ATTR_CONFLICT_RES = Use Requestor
    IGNORE_NULLS = No
    MERGED -> Sorter
FeatureMerger_2
    REJECT_NULL_MISSING_KEYS = No
    ATTR_ACCUM_MODE = Merge Supplier
    PROCESS_DUPS = No
    SUPPLIERS_FIRST = No
    JOIN_KEYS = @Value(__gnr) @Value(GNR) AUTO @Value(__bnr) @Value(BNR) AUTO @Value(__fnr) @Value(FNR) AUTO @Value(__snr) @Value(SNR) AUTO
    MERGE_TYPE = Attributes Only
    ATTR_CONFLICT_RES = Use Requestor
    IGNORE_NULLS = No
    MERGED -> Sorter

FME custom transformer WI02297104

Parameters:
- Ordrenavn =
- __GNR = @Value(__gnr)   # Gnr
- __BNR = @Value(__bnr)   # Bnr

Input (input)
    -> WorkspaceRunner_10
    -> WorkspaceRunner_6
WorkspaceRunner_10
    WORKSPACE_PARAMETERS = gnr,@Value(__gnr),bnr,@Value(__bnr),Ordrenavn,$(Ordrenavn)
    BLOCKING = Yes
    WORKSPACE_FILE = $(FME_MF_DIR)Ferdigattest_mb_2.fmw
    SUCCEEDED -> WorkspaceRunner_10_Succeeded (output)
    FAILED -> Counter
WorkspaceRunner_6
    WORKSPACE_PARAMETERS = gnr,@Value(__gnr),bnr,@Value(__bnr),Ordrenavn,$(Ordrenavn)
    BLOCKING = Yes
    WORKSPACE_FILE = $(FME_MF_DIR)Ferdigattest.fmw
    SUCCEEDED -> WorkspaceRunner_10_Succeeded (output)
    FAILED -> Counter
WorkspaceRunner_10_Succeeded (output)
Counter
    CNT_ATTR = W7104
    START = 1
    SCOPE = Global
    DOMAIN = W7104
    -> Tester
Tester
    TEST_DESCRIPTION = ""
    BOOL_OP = OR
    TEST_MODE = Automatic
    TEST_CLAUSE = TEST @Value(W7104) = 2
    PASSED -> WorkspaceRunner_6_Failed (output)
WorkspaceRunner_6_Failed (output)

FME custom transformer Situasjonskart
Collects all members of situasjonskart

Parameters:
- Ordrenavn =
- __BNR = @Value(__bnr)   # Bnr
- __FNR = @Value(__fnr)   # Fnr
- _ADRESSE = @Value(_adresse)   # Adresse
- __GNR = @Value(__gnr)   # Gnr
- __SNR = @Value(__snr)   # Snr

Input (input)
    -> WorkspaceRunner_sitkart_1-1000
    -> WorkspaceRunner_sitkart_1-500
    -> WorkspaceRunner_Detaljplan
    -> WorkspaceRunner_Komplan
    -> WorkspaceRunner_Temakart_1-1000
WorkspaceRunner_sitkart_1-1000
    WORKSPACE_PARAMETERS = DestDataset_PDF2D,$(FME_MF_DIR_ENCODED)ftp\upload\$(Ordrenavn)_sitkart_1-1000.pdf,SCALE,1000,GNR,@Value(__gnr),BNR,@Value(__bnr),FNR,@Value(__fnr),SNR,@Value(__snr),ADRESSE,@Value(_adresse),WMS_layer,ADRESSE,GNRBNR,AREALBRUK,PLAN_STREK,BANE,EIENDOMSKART,BYGNING,PBLTILTAK,BYGNANLEGG,GATENAVN,NATURINFO,TEKST,LEDNING,LEDNING_HOYSPENT,TRAKTORVEISTI,VEG,LEDNINGVA,TERRENG1,VANN
    BLOCKING = Yes
    WORKSPACE_FILE = $(FME_MF_DIR)Situasjonskart_2017.fmw
    SUCCEEDED -> FeatureHolder
    FAILED -> Counter_2
WorkspaceRunner_sitkart_1-500
    WORKSPACE_PARAMETERS = DestDataset_PDF2D,$(FME_MF_DIR_ENCODED)ftp\upload\$(Ordrenavn)_sitkart_1-500.pdf,SCALE,500,GNR,@Value(__gnr),BNR,@Value(__bnr),FNR,@Value(__fnr),SNR,@Value(__snr),ADRESSE,@Value(_adresse),WMS_layer,ADRESSE,GNRBNR,AREALBRUK,PLAN_STREK,BANE,EIENDOMSKART,BYGNING,PBLTILTAK,BYGNANLEGG,GATENAVN,NATURINFO,TEKST,LEDNING,LEDNING_HOYSPENT,TRAKTORVEISTI,VEG,LEDNINGVA,TERRENG1,VANN
    BLOCKING = Yes
    WORKSPACE_FILE = $(FME_MF_DIR)Situasjonskart_2017.fmw
    SUCCEEDED -> FeatureHolder
    FAILED -> Counter_2
WorkspaceRunner_Detaljplan
    WORKSPACE_PARAMETERS = DestDataset_PDF2D,$(FME_MF_DIR_ENCODED)ftp\upload\$(Ordrenavn)_detaljplan_1-1000.pdf,SCALE,1000,GNR,@Value(__gnr),BNR,@Value(__bnr),FNR,@Value(__fnr),SNR,@Value(__snr),ADRESSE,@Value(_adresse),WMS_layer,FKB_STREK,ADRESSE,GNRBNR,GATENAVN,RP3VN1,RP3VN2,RP3VN3,BP3VN1,BP3VN2,BP3VN3
    BLOCKING = Yes
    WORKSPACE_FILE = $(FME_MF_DIR)Situasjonskart_2017.fmw
    SUCCEEDED -> FeatureHolder
    FAILED -> Counter_2
WorkspaceRunner_Komplan
    WORKSPACE_PARAMETERS = DestDataset_PDF2D,$(FME_MF_DIR_ENCODED)ftp\upload\$(Ordrenavn)_komplan_1-1000.pdf,SCALE,1000,GNR,@Value(__gnr),BNR,@Value(__bnr),FNR,@Value(__fnr),SNR,@Value(__snr),ADRESSE,@Value(_adresse),WMS_layer,FKB_STREK,ADRESSE,GNRBNR,GATENAVN,KP3
    BLOCKING = Yes
    WORKSPACE_FILE = $(FME_MF_DIR)Situasjonskart_2017.fmw
    SUCCEEDED -> FeatureHolder
    FAILED -> Counter_2
WorkspaceRunner_Temakart_1-1000
    WORKSPACE_PARAMETERS = DestDataset_PDF2D,$(FME_MF_DIR_ENCODED)ftp\upload\$(Ordrenavn)_temakart_1-1000.pdf,SCALE,1000,GNR,@Value(__gnr),BNR,@Value(__bnr),FNR,@Value(__fnr),SNR,@Value(__snr),ADRESSE,@Value(_adresse),WMS_layer,FKB_STREK,ADRESSE,GNRBNR,GATENAVN,KULTUR,NATUR,FLOMSONER,RESTRIKSJONER
    BLOCKING = Yes
    WORKSPACE_FILE = $(FME_MF_DIR)Situasjonskart_2017.fmw
    SUCCEEDED -> FeatureHolder
    FAILED -> Counter_2
FeatureHolder
    -> Sampler
Sampler
    SAMPLE_MODE = No
    RATE = 1
    SAMPLE_TYPE_LONG = First N Features
    SAMPLED -> Succeeded (output)
Succeeded (output)
Counter_2
    CNT_ATTR = SitCount
    START = 1
    SCOPE = Global
    DOMAIN = SitCount
    -> Tester
Tester
    TEST_DESCRIPTION = ""
    BOOL_OP = OR
    TEST_MODE = Automatic
    TEST_CLAUSE = TEST @Value(SitCount) = 5
    PASSED -> Failed (output)
Failed (output)

FME custom transformer WI02297112

Parameters:
- Ordrenavn =
- __SNR = @Value(__snr)   # Snr
- _ORDRENAVN = @Value(_Ordrenavn)   # Ordrenavn
- __FNR = @Value(__fnr)   # Fnr
- __GNR = @Value(__gnr)   # Gnr
- __BNR = @Value(__bnr)   # Bnr
- ORDERID = @Value(OrderId)   # OrderId
- _REFERANSE = @Value(_Referanse)   # Referanse

WorkspaceRunner_6_Input (input)
    -> WorkspaceRunner_6
WorkspaceRunner_6
    WORKSPACE_PARAMETERS = Ordrenavn,@Value(_Ordrenavn),GNR,@Value(__gnr),BNR,@Value(__bnr),FNR,@Value(__fnr),SNR,@Value(__snr),ref,@Value(_Referanse),DestDataset_TEXTLINE,$(FME_MF_DIR_USERTYPED)ftp\upload\xml\resultset_2473_@Value(OrderId).xml
    BLOCKING = Yes
    WORKSPACE_FILE = $(FME_MF_DIR)KommunaleGebyrer_xml.fmw
    SUCCEEDED -> WorkspaceRunner_4
    FAILED -> WorkspaceRunner_4
WorkspaceRunner_4
    WORKSPACE_PARAMETERS = GNR,@Value(__gnr),BNR,@Value(__bnr),FNR,@Value(__fnr),SNR,@Value(__snr),ref,@Value(_Referanse),msdocfile,$(FME_MF_DIR_ENCODED)ftp\upload\$(Ordrenavn).docx,Ordrenavn,@Value(_Ordrenavn)
    BLOCKING = Yes
    WORKSPACE_FILE = $(FME_MF_DIR)KommunaleGebyrer.fmw
    SUCCEEDED -> WorkspaceRunner_4_Succeeded (output)
    FAILED -> WorkspaceRunner_4_Failed (output)
WorkspaceRunner_4_Succeeded (output)
WorkspaceRunner_4_Failed (output)
