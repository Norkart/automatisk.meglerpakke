FME workspace Grunnkart_v3.fmw

Parameters:
- DestDataset_PDF2D = $(FME_MF_DIR_USERTYPED)test\g3.pdf   # Destination PDF File
- _gnr = 115   # Gnr
- _bnr = 232   # Bnr
- _fnr = 0   # Fnr
- _snr = 1   # Snr
- A4 = YES   # A4 proportion
- DestDataset_SQLITE3 = X:\Data\SQLITE\0229_UTVALG_EIENDOM.sl3   # Destination SQLite Database File

Writers:
- PDF2D_1: PDF2D to $(DestDataset_PDF2D)

Creator
    NUM = 1
    GEOMTYPE = Geometry Object
    CREATED -> ParameterFetcher
ParameterFetcher
    ATTR_LIST = GNR {$(_gnr)} BNR {$(_bnr)} FNR {$(_fnr)} SNR {$(_snr)}
    -> WorkspaceRunner
WorkspaceRunner
    WORKSPACE_FILE = $(FME_MF_DIR)UTVALG_EIENDOM.fmw
    BLOCKING = Yes
    WORKSPACE_PARAMETERS = GNR,$(_gnr),BNR,$(_bnr),FNR,$(_fnr),SNR,$(_snr),DestDataset_SQLITE3,$(DestDataset_SQLITE3)
    SUCCEEDED -> FeatureReader [INITIATOR]
    FAILED -> WorkspaceRunner_2
WorkspaceRunner_2
    WORKSPACE_FILE = $(FME_MF_DIR)UTVALG_EIENDOM.fmw
    BLOCKING = Yes
    WORKSPACE_PARAMETERS = GNR,$(_gnr),BNR,$(_bnr),FNR,$(_fnr),SNR,0,DestDataset_SQLITE3,$(DestDataset_SQLITE3)
    SUCCEEDED -> FeatureReader [INITIATOR]
FeatureReader
    ATTR_ACCUM_MODE = Only Use Result
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    SPATIALITE_QUERY_FEATURE_TYPES_FOR_MERGE_FILTERS = Yes
    COMBINE_GEOM = Use Result
    FEATURETYPES = Teig
    DATASET = $(DestDataset_SQLITE3)
    OUTPUT_FEATURES_DISPLAY = Schema and Data Features
    FORMAT = SPATIALITE
    INTERACT = <No Spatial Filter>
    Teig -> BoundingBoxReplacer_2
    Teig -> MerkEiendom
MerkEiendom
    _bnr = $(_bnr)
    _gnr = $(_gnr)
    _snr = $(_snr)
    _fnr = $(_fnr)
    label -> MapnikRasterizer [Label00]
    Line -> MapnikRasterizer [Teig]
    Polygon -> MapnikRasterizer [Teig00]
BoundingBoxReplacer_2
    BOXTYPE = Bounding Box
    BOX -> Tester
Tester
    TEST_CLAUSE = TEST @Area() < 50000
    TEST_DESCRIPTION = ""
    BOOL_OP = OR
    TEST_MODE = Automatic
    PASSED -> WMS_3
    FAILED -> Terminator
WMS_3
    ratio_l = 271.75
    A4 = YES
    WMS_layer = GATENAVN,MATRIKKEL_KART,VEG_STREK,VANN_STREK
    ratio_s = 210.0
    WMS_url = http://195.1.20.83/wms-follo
    -> Ramme [BoundingBoxAccumulator_Input]
    -> MeasureLineCreator
    -> Bounding
    -> MapnikRasterizer [Output]
    -> TextRepalcer
Note: TextRepalcer [TextRepalcer] / [Embedded] / BNR: @Value(BNR) / FNR: @Value(FNR) / GNR: @Value(GNR) / SNR: @Value(SNR)
TextRepalcer
    FNR = @Value(FNR)
    GNR = @Value(GNR)
    SNR = @Value(SNR)
    BNR = @Value(BNR)
    Output_2 -> MapnikRasterizer [Output_2]
    Dato -> MapnikRasterizer [Output_3]
MeasureLineCreator
    Line -> MapnikRasterizer [Line]
    Label -> MapnikRasterizer [Label]
Bounding
    Higth = 24
    -> MapnikRasterizer [Top_layout]
    -> Ramme [BoundingBoxAccumulator_Input]
Ramme
    BoundsExtractor_Output -> MapnikRasterizer [Coerced]
    BoundsExtractor_Output -> BoundingBoxReplacer
MapnikRasterizer
    GROUND_EXTENTS_MAX_X = @Value(ymin)
    SPACING = 0.1
    INTERPRETATION_TYPE = RGBA32
    BACKGROUND_COLOR_ALPHA = 1.0
    BACKGROUND_COLOR = 1,1,1
    MAPNIK_CONFIG = Top_layout;raster;__ignore__raster-properties-group;;opacity;1;scaling;near;__ignore__comp-group;;comp-op;src-over;Output;raster;__ignore__raster-properties-group;;opacity;1;scaling;near;__ignore__comp-group;;comp-op;src-over;Output_2;text;__ignore__text-properties-group;;name;gnavn;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Output_3;text;__ignore__text-properties-group;;name;_timestamp;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Coerced;line;__ignore__color-group;;stroke;0,0,0;stroke-opacity;1;__ignore__line-style-group;;stroke-width;9;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Line;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over;Teig00;polygon;__ignore__color-group;;fill;1,0.607843,0.607843;fill-opacity;0.3;__ignore__smoothing-group;FME_DISCLOSURE_OPEN;gamma;1;gamma-method;linear;smooth;0;__ignore__comp-group;FME_DISCLOSURE_OPEN;comp-op;src-over;Teig;line;__ignore__color-group;;stroke;1,0,0;stroke-opacity;1;__ignore__line-style-group;;stroke-width;3;stroke-linejoin;miter;stroke-linecap;butt;stroke-dasharray;"12 6";stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Label00;text;__ignore__text-properties-group;;name;salgsobjekt;face-name;Tahoma,Normal;size;10;__ignore__color-group;;fill;1,0,0;opacity;1;halo-fill;1,1,1;halo-radius;0;__ignore__positioning-group;;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;;comp-op;src-over;Label;text;__ignore__text-properties-group;;name;label;face-name;Tahoma,Normal;size;@Evaluate(4*@Value(dy));__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;middle;justify-alignment;center;vertical-alignment;top;__ignore__comp-group;;comp-op;src-over
    GROUND_EXTENTS_MAX_Y = @Value(ymax)
    COLROW_OR_SPACING = Spacing
    SPECIFY_GROUND_EXTENTS = Specify ground extents
    LAYER_CARDINALITY = Each rendering rule is a layer
    GROUND_EXTENTS_MIN_X = @Value(xmin)
    GROUND_EXTENTS_MIN_Y = @Value(xmax)
    RASTER -> Clipper [CLIPPEE]
BoundingBoxReplacer
    BOXTYPE = Bounding Box
    BOX -> Clipper [CLIPPER]
Clipper
    BOUNDARY_CASES = Treat as Inside
    PRESERVE_CLIPPEE_EXTENTS = No
    CLIPPED_ATTR = _clipped
    CREATE_AGGREGATES = Yes
    CLIP_TYPE = Multiple Clippers
    LINES_AS_SEGMENTS = No
    CONNECT_Z_MODE = First Wins
    INSIDE -> PDFPageFormatter [Inside]
PDFPageFormatter
    PAGE_UNITS = Centimeters
    PAGE_WIDTH_USER = 21
    PAGE_SIZE = A4
    PAGE_HEIGHT_PTS = 842
    PAGE_OBJECTS = "Inside WIDTH;566.93;FIXED_ASPECT;Yes;SIZE_PARAMS;;MINY;14.29;MINX;14.17;HEIGHT;813.54;CLIPPING_ENABLED;No;SCALING_PARAMS;"
    PAGE_HEIGHT_USER = 29.7
    PAGE_NUMBER = 1
    PAGE_WIDTH_PTS = 595
    PAGE_ORIENTATION = Portrait
    -> Teig (writer PDF2D_1)
Teig (writer PDF2D_1)
Terminator
    MESSAGE = Translation Terminated

FME custom transformer MerkEiendom

Parameters:
- _gnr = 115   # Gnr
- _bnr = 312   # Bnr
- _fnr = 0   # Fnr
- _snr = 0   # Snr

Input (input)
    -> DonutHoleExtractor
    -> Polygon (output)
DonutHoleExtractor
    OUTERSHELL -> GeometryCoercer
    HOLE -> GeometryCoercer
GeometryCoercer
    GQUERY:
      for $geom in //geometry
      where $geom/count(parent::geometry) = 0
      return number($geom/@fme_id)
    KIND = fme_line
    COERCED -> AttributeCreator
    COERCED -> Line (output)
AttributeCreator
    ATTR_TABLE = SET_TO salgsobjekt = Salgs objekt!
    -> Chopper
Chopper
    MODE = By Length
    APPROX_LENGTH = 50
    GRID_AREAS = Yes
    CHOPPED_ATTR = _chopped
    -> OrientationExtractor
OrientationExtractor
    ORIENTATION = _orientation
    -> LabelPointReplacer
LabelPointReplacer
    LABATTR = @Value(salgsobjekt)
    HEIGHT = 20
    ALWAYSROTATE = no
    LabelPoint -> label (output)
label (output)
Line (output)
Polygon (output)

FME custom transformer Ramme

BoundingBoxAccumulator_Input (input)
    -> BoundingBoxAccumulator
BoundingBoxAccumulator
    ACCUM_ATTRS_NAME = Get Attributes From One Representative Feature
    TOPFER_INDEX = No
    BOUNDING_BOX -> GeometryCoercer
GeometryCoercer
    GQUERY:
      for $geom in //geometry
      where $geom/count(parent::geometry) = 0
      return number($geom/@fme_id)
    KIND = fme_line
    COERCED -> BoundsExtractor
BoundsExtractor
    XMIN = xmin
    XMAX = xmax
    YMIN = ymin
    YMAX = ymax
    -> BoundsExtractor_Output (output)
BoundsExtractor_Output (output)

FME custom transformer WMS_3

Parameters:
- WMS_url =
- WMS_layer =
- Username =   # Enter Username
- password =   # Enter password
- A4 = NO   # A4 proportion
- ratio_l = 229.75   # Length of long side
- ratio_s = 210.0   # Length of shorter side

Input (input)
    -> BoundsExtractor
BoundsExtractor
    XMIN = _hmin
    XMAX = _hmax
    YMIN = _vmin
    YMAX = _vmax
    -> Tester
Tester
    TEST_CLAUSE = TEST $(A4) = NO
    TEST_DESCRIPTION = ""
    BOOL_OP = OR
    TEST_MODE = Automatic
    PASSED -> AttributeCreator
    FAILED -> ParameterFetcher
ParameterFetcher
    ATTR_LIST = _ratio_l {$(ratio_l)} _ratio_s {$(ratio_s)}
    -> AttributeCreator_4
AttributeCreator_4
    ATTR_TABLE:
      SET_TO _ratio_l = @real64(@Value(_ratio_l))
      SET_TO _ratio_s = @real64(@Value(_ratio_s))
    -> PythonCaller
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self.hmax=feature.getAttribute('_hmax')
              self.hmin=feature.getAttribute('_hmin')
              self.vmax=feature.getAttribute('_vmax')
              self.vmin=feature.getAttribute('_vmin')

              self.dh=self.hmax-self.hmin
              self.dv=self.vmax-self.vmin

              self.hmean = (self.hmax + self.hmin)/2.0
              self.vmean = (self.vmax + self.vmin)/2.0

              if self.dv < feature.getAttribute('_ratio_l') and self.dh < feature.getAttribute('_ratio_s'):
                  self.vmin= self.vmean-feature.getAttribute('_ratio_l')/2.0
                  self.vmax= self.vmean+feature.getAttribute('_ratio_l')/2.0
                  self.hmin = self.hmean-feature.getAttribute('_ratio_s')/2.0
                  self.hmax = self.hmean+feature.getAttribute('_ratio_s')/2.0
              elif self.dh > self.dv and self.dv > feature.getAttribute('_ratio_l'):
                  self.ndv = self.dh*(feature.getAttribute('_ratio_l')/feature.getAttribute('_ratio_s'))
                  self.vmin= self.vmean-self.ndv/2.0
                  self.vmax= self.vmean+self.ndv/2.0
              elif self.dh < self.dv and self.dh > feature.getAttribute('_ratio_s'):
                  self.ndh  = self.dv*(feature.getAttribute('_ratio_s')/feature.getAttribute('_ratio_l'))
                  self.hmin = self.hmean-self.ndh/2.0
                  self.hmax = self.hmean+self.ndh/2.0
              else:
                  raise Exception('condition not met')
                  print 'condition not met'


              #self.dh=self.hmax-self.hmin
              #self.dv=self.vmax-self.vmin

              #print self.dh, self.dv

              feature.setAttribute('_hmax',self.hmax)
              feature.setAttribute('_hmin',self.hmin)
              feature.setAttribute('_vmax',self.vmax)
              feature.setAttribute('_vmin',self.vmin)
              self.pyoutput(feature)
          def close(self):
              pass
    PYTHONSYMBOL = FeatureProcessor
    -> VertexCreator
VertexCreator
    XVAL = @Value(_hmin)
    YVAL = @Value(_vmin)
    MODE_NAME = Replace with Point
    -> VertexCreator_2
VertexCreator_2
    XVAL = @Value(_hmax)
    YVAL = @Value(_vmax)
    MODE_NAME = Add Point
    -> BoundingBoxReplacer
BoundingBoxReplacer
    BOXTYPE = Bounding Box
    BOX -> AttributeCreator
AttributeCreator
    ATTR_TABLE:
      SET_TO h_t = @Evaluate(@round((@Value(_hmax)-@Value(_hmin))/200)+1)
      SET_TO v_t = @Evaluate(@round((@Value(_vmax)-@Value(_vmin))/200)+1)
      SET_TO dh = @Evaluate(@Value(_hmax)-@Value(_hmin))
      SET_TO dv = @Evaluate(@Value(_vmax)-@Value(_vmin))
    -> Tester_2
Tester_2
    TEST_CLAUSE:
      TEST @Value(dv) > 1000
      TEST @Value(dh) > 1000
    TEST_DESCRIPTION = ""
    BOOL_OP = OR
    TEST_MODE = Automatic
    PASSED -> Tiler
    FAILED -> AttributeRemover_3
Tiler
    XINC = 1000
    BOUNDARY_CASES = No
    TILING_TYPE = Tile Size
    YINC = 1000
    COL_ATTR = _column
    ROW_ATTR = _row
    TILED -> AttributeRemover
AttributeRemover
    REMOVE_ATTRS = _vmax,_vmin,_column,h_t,_hmax,_hmin,v_t,_row
    -> BoundsExtractor_2
BoundsExtractor_2
    XMIN = _xmin
    XMAX = _xmax
    YMIN = _ymin
    YMAX = _ymax
    -> AttributeRounder
AttributeRounder
    SRC_ATTRS = _xmax _ymax
    ROUND_TYPE = Up
    PLACES = 0
    -> AttributeRounder_2
AttributeRounder_2
    SRC_ATTRS = _xmin _ymin
    ROUND_TYPE = Down
    PLACES = 0
    -> AttributeCreator_2
AttributeCreator_2
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*3)&HEIGHT=@Evaluate((@Value(_ymax)-@Value(_ymin))*3)&SRS=EPSG:25832&TRANSPARENT=true&BBOX=@Value(_xmin),@Value(_ymin),@Value(_xmax),@Value(_ymax)&
    -> HTTPCaller_3
HTTPCaller_3
    SAVE_FILE = Attribute
    RESPONSE_HEADER_LIST_ATTR = _headers
    FOLLOW_REDIRECTS = Yes
    AUTH_USERNAME = $(Username)
    CONNECTION_TIMEOUT_LENGTH = 60
    AUTH_METHOD = Basic
    STATUS_CODE_ATTR = _http_status_code
    TRANSFER_TIMEOUT_LENGTH = 90
    AUTH_PASSWORD = $(password)
    ERROR_ATTR = _error
    HTTP_METHOD = GET
    VERIFY_SSL_CERTIFICATES = Yes
    USE_COOKIES = No
    TARGET_URL = @Value(_wms2)
    TARGET_ATTR_ENCODING = auto-detect
    TARGET_ATTR = _response_body
    -> RasterReplacer_2
AttributeRemover_3
    REMOVE_ATTRS = _hmin,_vmax,_vmin,dv,v_t,dh,_hmax,h_t
    -> BoundsExtractor_3
BoundsExtractor_3
    XMIN = _xmin
    XMAX = _xmax
    YMIN = _ymin
    YMAX = _ymax
    -> AttributeRounder_3
AttributeRounder_3
    SRC_ATTRS = _xmax _ymax
    ROUND_TYPE = Up
    PLACES = 0
    -> AttributeRounder_4
AttributeRounder_4
    SRC_ATTRS = _xmin _ymin
    ROUND_TYPE = Down
    PLACES = 0
    -> AttributeCreator_3
AttributeCreator_3
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*4)&HEIGHT=@Evaluate((@Value(_ymax)-@Value(_ymin))*4)&SRS=EPSG:25832&TRANSPARENT=true&BBOX=@Value(_xmin),@Value(_ymin),@Value(_xmax),@Value(_ymax)&
    -> HTTPCaller_2
HTTPCaller_2
    SAVE_FILE = Attribute
    RESPONSE_HEADER_LIST_ATTR = _headers
    FOLLOW_REDIRECTS = Yes
    AUTH_USERNAME = $(Username)
    CONNECTION_TIMEOUT_LENGTH = 60
    AUTH_METHOD = Basic
    STATUS_CODE_ATTR = _http_status_code
    TRANSFER_TIMEOUT_LENGTH = 90
    AUTH_PASSWORD = $(password)
    ERROR_ATTR = _error
    HTTP_METHOD = GET
    VERIFY_SSL_CERTIFICATES = Yes
    USE_COOKIES = No
    TARGET_URL = @Value(_wms)
    TARGET_ATTR_ENCODING = auto-detect
    TARGET_ATTR = _response_body
    -> RasterReplacer_2
RasterReplacer_2
    FORMAT = PNGRASTER
    BLOB_ATTR = _response_body
    REMOVE_ATTRIBUTE = No
    -> RasterCheckpointer
RasterCheckpointer
    -> RasterGeoreferencer_2
RasterGeoreferencer_2
    X_UL_COORD = @Value(_xmin)
    X_LL_COORD = @Value(_xmin)
    Y_LL_COORD = @Value(_ymin)
    Y_UL_COORD = @Value(_ymax)
    Y_UR_COORD = @Value(_ymax)
    POINTANDANGLE_OR_EXTENTS = Extents
    X_LR_COORD = @Value(_xmax)
    X_UR_COORD = @Value(_xmax)
    Y_LR_COORD = @Value(_ymin)
    -> AttributeRemover_2
AttributeRemover_2
    LIST_ATTRS = _headers{} _headers{}.name _headers{}.value
    REMOVE_ATTRS = _ymax,_xmax,_ymin,_wms,_wms2,dv,_http_status_code,_xmin,dh,_response_body
    -> RasterCheckpointer_2
RasterCheckpointer_2
    -> RasterMosaicker
RasterMosaicker
    INTERPOLATION_TYPE_NAME = Nearest Neighbor
    COMPOSITE_USING_ALPHA_BAND_NAME = No
    NODATA_OVERWRITE = No
    SNAPPING_TYPE_NAME = Resample
    MERGE_PALETTES_NAME = Yes
    ACCUM_ATTRS_NAME = Get Attributes From One Representative Feature
    -> Output (output)
Output (output)

FME custom transformer Bounding

Parameters:
- Higth =   # Hight Frame

Input (input)
    -> BoundsExtractor
BoundsExtractor
    ZMIN = _zmin
    XMIN = _xmin
    XMAX = _xmax
    YMIN = _ymin
    YMAX = _ymax
    ZMAX = _zmax
    -> ParameterFetcher
ParameterFetcher
    ATTR_LIST = _Higth {$(Higth)}
    -> PythonCaller
PythonCaller
    NEW_ATTRIBUTES = _ymin _ymax
    PYTHONSOURCE:
      import fme
      import fmeobjects
      # Template Function interface:
      def processFeature(feature):
          pass

      # Template Class Interface:
      class FeatureProcessor(object):
          def __init__(self):
              self.y0=0
              self.y1=0
          def input(self,feature):
              self.y0 = float(feature.getAttribute('_ymax'))
              self.y  = float(feature.getAttribute('_ymin'))
              self.dy=self.y0 - self.y

              self.y1=self.y0+float(feature.getAttribute('_Higth'))*self.dy/252.0

              feature.setAttribute('_ymin',self.y0)
              feature.setAttribute('_ymax',self.y1)
              self.pyoutput(feature)
          def close(self):
              del self
    PYTHONSYMBOL = FeatureProcessor
    -> VertexCreator
VertexCreator
    XVAL = @Value(_xmin)
    YVAL = @Value(_ymin)
    MODE_NAME = Replace with Point
    -> VertexCreator_4
VertexCreator_4
    XVAL = @Value(_xmax)
    YVAL = @Value(_ymax)
    MODE_NAME = Add Point
    -> BoundsExtractor_2
BoundsExtractor_2
    ZMIN = _zmin
    XMIN = _xmin
    XMAX = _xmax
    YMIN = _ymin
    YMAX = _ymax
    ZMAX = _zmax
    -> FeatureReader [INITIATOR]
FeatureReader
    JPEG_APPLY_GCPS = No
    JPEG_CLIP_TO_ENVELOPE = NO
    ATTR_ACCUM_MODE = Only Use Result
    ATTRIBUTES = JPEG,exif_artist
    COMBINE_GEOM = Use Result
    DATASET = $(FME_MF_DIR_ENCODED)Layout\Meglerkart-Grunnkart.JPG
    JPEG_GROUP_BY_DATASET = No
    OUTPUT_FEATURES_DISPLAY = Schema and Data Features
    JPEG_USE_SEARCH_ENVELOPE = NO
    FORMAT = JPEG
    INTERACT = <No Spatial Filter>
    JPEG -> Counter_2
    INITIATOR -> Counter
Counter_2
    DOMAIN = id
    SCOPE = Local
    START = 0
    CNT_ATTR = id
    -> FeatureMerger [REQUESTOR]
Counter
    DOMAIN = id
    SCOPE = Local
    START = 0
    CNT_ATTR = id
    -> FeatureMerger [SUPPLIER]
FeatureMerger
    IGNORE_NULLS = No
    PROCESS_DUPS = No
    ATTR_CONFLICT_RES = Use Requestor
    REJECT_NULL_MISSING_KEYS = No
    MERGE_TYPE = Attributes Only
    ATTR_ACCUM_MODE = Merge Supplier
    SUPPLIERS_FIRST = No
    JOIN_KEYS = @Value(id) @Value(id) AUTO
    MERGED -> RasterGeoreferencer
RasterGeoreferencer
    X_UL_COORD = @Value(_xmin)
    X_LL_COORD = @Value(_xmin)
    Y_LL_COORD = @Value(_ymin)
    Y_UL_COORD = @Value(_ymax)
    Y_UR_COORD = @Value(_ymax)
    POINTANDANGLE_OR_EXTENTS = Extents
    X_LR_COORD = @Value(_xmax)
    X_UR_COORD = @Value(_xmax)
    Y_LR_COORD = @Value(_ymin)
    -> AttributeRemover
AttributeRemover
    REMOVE_ATTRS = _zmin,_ymin,_zmax,_xmax,pdf_page_number,_xmin,_ymax
    -> Output (output)
Output (output)

FME custom transformer TextRepalcer
Adds a number layer on each side.

Parameters:
- BNR = @Value(BNR)
- FNR = @Value(FNR)
- GNR = @Value(GNR)
- SNR = @Value(SNR)

Input (input)
    -> BoundingBoxReplacer
BoundingBoxReplacer
    BOXTYPE = Bounding Box
    BOX -> BoundsExtractor
BoundsExtractor
    ZMIN = _zmin
    XMIN = _xmin
    XMAX = _xmax
    YMIN = _ymin
    YMAX = _ymax
    ZMAX = _zmax
    -> PythonCaller_2
PythonCaller_2
    NEW_ATTRIBUTES = _xmin _ymax _xmax _ymin text_hight
    PYTHONSOURCE:
      import fme
      import fmeobjects
      # Template Function interface:
      def processFeature(feature):
          pass

      # Template Class Interface:
      class FeatureProcessor(object):
          def __init__(self):
              pass
          def input(self,feature):
              self.y0=feature.getAttribute('_ymax')
              self.y=feature.getAttribute('_ymin')

              self.y1=self.y0+9*(self.y0-self.y)/252
              self.y2=self.y0+3*(self.y0-self.y)/252
              self.hight=30*(self.y0-self.y)/252

              self.x=feature.getAttribute('_xmax')
              self.x0=feature.getAttribute('_xmin')

              self.x1=self.x0+39*(self.x-self.x0)/190
              self.x2=self.x0+39*(self.x-self.x0)/190 #tidligere + 97


              feature.setAttribute('_xmin',self.x1)
              feature.setAttribute('_ymax',self.y1)
              feature.setAttribute('_ymin',self.y2)
              feature.setAttribute('_xmax',self.x2)
              feature.setAttribute('text_hight',self.hight)

              self.pyoutput(feature)
          def close(self):
              del self
    PYTHONSYMBOL = FeatureProcessor
    -> VertexCreator_2
    -> VertexCreator_4
VertexCreator_2
    XVAL = @Value(_xmin)
    YVAL = @Value(_ymax)
    MODE_NAME = Replace with Point
    INDEX = 0
    -> StringFormatter
StringFormatter
    FORMAT = 4s
    SRC_ATTRS = GNR,BNR,SNR,FNR
    -> AttributeCreator
AttributeCreator
    ATTR_LIST = gnavn,GNR: @Value(GNR) BNR: @Value(BNR) FNR: @Value(FNR) SNR: @Value(SNR)
    -> LabelPointReplacer_2
LabelPointReplacer_2
    LABATTR = @Value(gnavn)
    HEIGHT = @Value(text_hight)
    ALWAYSROTATE = yes
    LabelPoint -> Output_2 (output)
Output_2 (output)
VertexCreator_4
    XVAL = @Value(_xmax)
    YVAL = @Value(_ymin)
    MODE_NAME = Replace with Point
    INDEX = 0
    -> TimeStamper
TimeStamper
    FMT = ^d.^m.^Y
    TIME_ATTR = _timestamp
    -> AttributeCreator_2
AttributeCreator_2
    ATTR_TABLE = SET_TO _timestamp = Dato: @Value(_timestamp)        Enebakk Kommune
    -> LabelPointReplacer_3
LabelPointReplacer_3
    LABATTR = @Value(_timestamp)
    HEIGHT = @Value(text_hight)
    ALWAYSROTATE = yes
    LabelPoint -> Dato (output)
Dato (output)

FME custom transformer MeasureLineCreator

Input (input)
    -> BoundsExtractor
BoundsExtractor
    XMIN = _xmin
    XMAX = _xmax
    YMIN = _ymin
    YMAX = _ymax
    -> AttributeCreator
AttributeCreator
    ATTR_TABLE:
      SET_TO size = @ceil(@Evaluate(@Value(_xmax)-@Value(_xmin))/5)
      SET_TO dy = @floor(@Evaluate((@Value(_ymax)-@Value(_ymin))/15))
      SET_TO dx = @floor(@Evaluate((@Value(_ymax)-@Value(_ymin))/15))
    -> TestFilter
TestFilter
    DEFAULT_VALUE = <UNFILTERED>
    TEST_LIST:
      BOOL_OP,AND,COMPOSITE_TEST,<Unused>,TEST_CLAUSE,"TEST @Value(size) >= 0
      TEST @Value(size) < 100",< 100,BOOL_OP,AND,COMPOSITE_TEST,<Unused>,TEST_CLAUSE,"TEST @Value(size) >= 100
      TEST @Value(size) < 1000",< 1000,BOOL_OP,AND,COMPOSITE_TEST,<Unused>,TEST_CLAUSE,"TEST @Value(size) >= 1000
      TEST @Value(size) < 10000",< 10000,BOOL_OP,AND,COMPOSITE_TEST,<Unused>,TEST_CLAUSE,"TEST @Value(size) >= 10000
      TEST @Value(size) < 100000",< 100000
    < 100 -> AttributeRounder
    < 1000 -> AttributeRounder_2
    < 10000 -> AttributeRounder_3
    < 100000 -> AttributeRounder_4
AttributeRounder
    SRC_ATTRS = size
    ROUND_TYPE = Nearest
    PLACES = -1
    -> VertexCreator
AttributeRounder_2
    SRC_ATTRS = size
    ROUND_TYPE = Nearest
    PLACES = -2
    -> VertexCreator
VertexCreator
    XVAL = @Evaluate(@Value(_xmax)-@Value(dx))
    YVAL = @Evaluate(@Value(_ymin)+@Value(dy))
    MODE_NAME = Replace with Point
    -> VertexCreator_2
    -> VertexCreator_5
VertexCreator_5
    XVAL = @Evaluate(@Value(_xmax)-@Value(dx))
    YVAL = @Evaluate(@Value(_ymin)+2*@Value(dy))
    MODE_NAME = Add Point
    -> Line (output)
VertexCreator_2
    XVAL = @Evaluate(@Value(_xmax)-@Value(dx)-@Value(size))
    YVAL = @Evaluate(@Value(_ymin)+@Value(dy))
    MODE_NAME = Add Point
    -> AttributeCreator_2
    -> VertexCreator_6
VertexCreator_6
    XVAL = @Evaluate(@Value(_xmax)-@Value(dx)-@Value(size))
    YVAL = @Evaluate(@Value(_ymin)+2*@Value(dy))
    MODE_NAME = Add Point
    -> Line (output)
AttributeCreator_2
    ATTR_TABLE = SET_TO BENEVNING = m
    -> Line (output)
    -> AttributeCreator_4
Line (output)
AttributeRounder_3
    SRC_ATTRS = size
    ROUND_TYPE = Nearest
    PLACES = -3
    -> VertexCreator_3
AttributeRounder_4
    SRC_ATTRS = size
    ROUND_TYPE = Nearest
    PLACES = -4
    -> VertexCreator_3
VertexCreator_3
    XVAL = @Evaluate(@Value(_xmax)-@Value(dx))
    YVAL = @Evaluate(@Value(_ymin)+@Value(dy))
    MODE_NAME = Replace with Point
    -> VertexCreator_4
VertexCreator_4
    XVAL = @Evaluate(@Value(_xmax)-@Value(dx)-@Value(size))
    YVAL = @Evaluate(@Value(_ymin)+@Value(dy))
    MODE_NAME = Add Point
    -> AttributeCreator_3
AttributeCreator_3
    ATTR_TABLE:
      SET_TO BENEVNING = Km
      SET_TO size = @Evaluate(@Value(size)/1000)
    -> AttributeCreator_4
AttributeCreator_4
    ATTR_TABLE = SET_TO label = @int(@Value(size))@Value(BENEVNING)
    -> LabelPointReplacer
LabelPointReplacer
    LABATTR = @Value(label)
    HEIGHT = @Evaluate(2*@Value(dy))
    ALWAYSROTATE = yes
    LabelPoint -> Label (output)
Label (output)
