FME workspace Ferdigattest.fmw

Parameters:
- gnr = 6   # Gårdsnr
- bnr = 201   # Bruksnr
- Ordrenavn = 6-201
- PASSWORD = ZXasqw12   # Password ePhorte
- DestDataset_FILECOPY = $(FME_MF_DIR)Ferdigattest_fra_ePhorte   # Destination File Copy Folder

Readers:
- MSSQL_ADO_1: MSSQL_ADO from skikommune@int-mssql-01.ansatt.oikt.net\ENE/EPHENE

Writers:
- FILECOPY_1: FILECOPY to $(DestDataset_FILECOPY)

dbo.DOKBESKRIV (reader MSSQL_ADO_1)
    attributes: DB_DOKID integer, DB_KATEGORI_DK varchar(10), DB_TITTEL varchar(255), DB_PAPIR smallint, DB_LOKPAPIR varchar(255), DB_STATUS_DS varchar(2), DB_UTARBAV_PN integer, DB_TGKODE_TK varchar(2), DB_UOFF varchar(70), DB_AGDATO datetime, DB_AGKODE_AG varchar(2), DB_TGGRUPPE_TG integer, DB_DIV0_G varchar(255), DB_DIV1_G varchar(255), DB_DIV2_G varchar(255), DB_DIV3_G varchar(255), DB_DIV4_G varchar(255), DB_DIV5_G varchar(255), DB_DIV6_G varchar(255), DB_DIV7_G varchar(255), DB_DIV8_G varchar(255), DB_DIV9_G varchar(255), DB_SISTOPPDATERT_G datetime, DB_PUBLISERT_G smallint, DB_OPPRETTETDATO_G datetime, DB_OPPRETTETAV_PN integer, DB_KASSKODE_KK varchar(2), DB_KASSDATO datetime, DB_BEVTID smallint, DB_KASSERTAV_PN smallint,
      DB_KASSERTDATO_G datetime
    -> AttributeManager_3
AttributeManager_3
    ATTR_TABLE:
      REMOVE DB_PAPIR
      REMOVE DB_LOKPAPIR
      REMOVE DB_STATUS_DS
      REMOVE DB_UTARBAV_PN
      REMOVE DB_TGKODE_TK
      REMOVE DB_UOFF
      REMOVE DB_AGDATO
      REMOVE DB_AGKODE_AG
      REMOVE DB_TGGRUPPE_TG
      REMOVE DB_DIV0_G
      REMOVE DB_DIV1_G
      REMOVE DB_DIV2_G
      REMOVE DB_DIV3_G
      REMOVE DB_DIV4_G
      REMOVE DB_DIV5_G
      REMOVE DB_DIV6_G
      REMOVE DB_DIV7_G
      REMOVE DB_DIV8_G
      REMOVE DB_DIV9_G
      REMOVE DB_SISTOPPDATERT_G
      REMOVE DB_PUBLISERT_G
      REMOVE DB_OPPRETTETDATO_G
      REMOVE DB_OPPRETTETAV_PN
      REMOVE DB_KASSKODE_KK
      REMOVE DB_KASSDATO
      REMOVE DB_BEVTID
      REMOVE DB_KASSERTAV_PN
      REMOVE DB_KASSERTDATO_G
    -> Joiner
Joiner
    TABLE = dbo.DOKLINK
    MATCH_RULE_DISPLAY = Match All (1:M)
    MATCH_MULTIPLE_DISPLAY = Create a feature for each match
    PREFETCH_EXHAUSTIVE = Yes
    MSSQL_ADO_COMMAND_TIMEOUT = 30
    MSSQL_ADO_NAMED_CONNECTION = skikommune@int-mssql-01.ansatt.oikt.net\ENE/EPHENE
    CACHE_SIZE = 5000
    ATTR_CONFLICT_RES = Use Original
    ADDED_FIELDS = DL_JPID_JP
    ATTR_ACCUM_MODE = Merge Joined
    MSSQL_ADO_QUERY_FEATURE_TYPES_FOR_MERGE_FILTERS = Yes
    FORMAT = MSSQL_ADO
    DATASET = skikommune@int-mssql-01.ansatt.oikt.net\ENE/EPHENE
    JOIN_KEYS = DB_DOKID DL_DOKID_DB
    JOINED -> Joiner_2
Joiner_2
    TABLE = dbo.DOKVERSJON
    MATCH_RULE_DISPLAY = Match All (1:M)
    MATCH_MULTIPLE_DISPLAY = Create a feature for each match
    PREFETCH_EXHAUSTIVE = Yes
    MSSQL_ADO_COMMAND_TIMEOUT = 30
    MSSQL_ADO_NAMED_CONNECTION = skikommune@int-mssql-01.ansatt.oikt.net\ENE/EPHENE
    CACHE_SIZE = 5000
    ATTR_CONFLICT_RES = Use Original
    ADDED_FIELDS = VE_DOKFORMAT_LF VE_OPPRETTETDATO_G VE_VARIANT_VF VE_VERSJON
    ATTR_ACCUM_MODE = Merge Joined
    MSSQL_ADO_QUERY_FEATURE_TYPES_FOR_MERGE_FILTERS = Yes
    FORMAT = MSSQL_ADO
    DATASET = skikommune@int-mssql-01.ansatt.oikt.net\ENE/EPHENE
    JOIN_KEYS = DB_DOKID VE_DOKID_DB
    JOINED -> Joiner_3
Joiner_3
    TABLE = dbo.JOURNPOST
    MATCH_RULE_DISPLAY = Match All (1:M)
    MATCH_MULTIPLE_DISPLAY = Create a feature for each match
    PREFETCH_EXHAUSTIVE = Yes
    MSSQL_ADO_COMMAND_TIMEOUT = 30
    MSSQL_ADO_NAMED_CONNECTION = skikommune@int-mssql-01.ansatt.oikt.net\ENE/EPHENE
    CACHE_SIZE = 5000
    ATTR_CONFLICT_RES = Use Original
    ADDED_FIELDS = JP_HARRESTANSE_G JP_INNHOLD_G JP_JAAR JP_JDATO JP_SAID JP_SEKNR
    ATTR_ACCUM_MODE = Merge Joined
    MSSQL_ADO_QUERY_FEATURE_TYPES_FOR_MERGE_FILTERS = Yes
    FORMAT = MSSQL_ADO
    DATASET = skikommune@int-mssql-01.ansatt.oikt.net\ENE/EPHENE
    JOIN_KEYS = DL_JPID_JP JP_ID
    JOINED -> Joiner_4
Joiner_4
    TABLE = dbo.NOARKSAK
    MATCH_RULE_DISPLAY = Match All (1:M)
    MATCH_MULTIPLE_DISPLAY = Create a feature for each match
    PREFETCH_EXHAUSTIVE = Yes
    MSSQL_ADO_COMMAND_TIMEOUT = 30
    MSSQL_ADO_NAMED_CONNECTION = skikommune@int-mssql-01.ansatt.oikt.net\ENE/EPHENE
    CACHE_SIZE = 5000
    ATTR_CONFLICT_RES = Use Original
    ADDED_FIELDS = SA_DATO SA_OFFTITTEL_G SA_SAAR SA_SEKNR SA_TITTEL SA_ID
    ATTR_ACCUM_MODE = Merge Joined
    MSSQL_ADO_QUERY_FEATURE_TYPES_FOR_MERGE_FILTERS = Yes
    FORMAT = MSSQL_ADO
    DATASET = skikommune@int-mssql-01.ansatt.oikt.net\ENE/EPHENE
    JOIN_KEYS = JP_SAID SA_ID
    JOINED -> Joiner_5
Joiner_5
    TABLE = dbo.KLASSERING
    MATCH_RULE_DISPLAY = Match All (1:M)
    MATCH_MULTIPLE_DISPLAY = Create a feature for each match
    PREFETCH_QUERY = SELECT * from dbo.[KLASSERING] where [KL_ORDNPRI] in ('TEK1','TEK2','GML','TEK-GML')
    PREFETCH_EXHAUSTIVE = Yes
    MSSQL_ADO_COMMAND_TIMEOUT = 30
    MSSQL_ADO_NAMED_CONNECTION = skikommune@int-mssql-01.ansatt.oikt.net\ENE/EPHENE
    CACHE_SIZE = 5000
    ATTR_CONFLICT_RES = Use Original
    ADDED_FIELDS = KL_ID KL_ORDNPRI KL_ORDNVER KL_SORT
    ATTR_ACCUM_MODE = Merge Joined
    MSSQL_ADO_QUERY_FEATURE_TYPES_FOR_MERGE_FILTERS = Yes
    FORMAT = MSSQL_ADO
    DATASET = skikommune@int-mssql-01.ansatt.oikt.net\ENE/EPHENE
    JOIN_KEYS = JP_SAID KL_SAID_SA
    JOINED -> Ferdigattest_3
Ferdigattest_3
    JP_INNHOLD_G_2 = @Value(DB_TITTEL)
    Ferdigattest -> AttributeCreator_10
AttributeCreator_10
    ATTR_LIST = LINK_dok1,http://INT-EPH-02/EPHENE/shared/aspx/GetDoc.aspx?VE_DOKID_DB=@Value(DB_DOKID)&VE_VERSJON=@Value(VE_VERSJON)&VE_VARIANT_VF=@Value(VE_VARIANT_VF)&VE_DOKFORMAT_LF=@Value(VE_DOKFORMAT_LF)&VE_STATUS_XX=F&EphorteDb=ENEEPH&database=ENEEPH,LINK,http://INT-EPH-02/EPHENE/locator/?SHOW=SA&SA_ID=@Value(SA_ID)&database=ENEEPH,Antall_-,@StringLength(@ReplaceRegEx(@Value(KL_ORDNVER),[^/]+,""))
    -> StringSearcher_2
StringSearcher_2
    CASE = no
    REGEXP = \d+
    STRING_TO_SEARCH = @Value(KL_ORDNVER)
    MATCHES_ATTR = gnr_bnr
    MATCHED -> AttributeCreator_11
AttributeCreator_11
    ATTR_TABLE:
      SET_TO GNR = @Value(gnr_bnr{0}.match)
      SET_TO BNR = @Value(gnr_bnr{1}.match)
      SET_TO FNR_OR_BNR2_OR_SNR = @Value(gnr_bnr{2}.match)
    -> Counter
Counter
    CNT_ATTR = _count_all
    DOMAIN = counter
    START = 0
    SCOPE = Local
    -> StatisticsCalculator
StatisticsCalculator
    PREPEND_ATTR_NAME_CHOICE = For multiple results only
    STATS_ATTRS = _count_all
    COMPUTE_HISTOGRAM = NO
    MAX_ATTR = _max
    COMPLETE -> Tester_2
Tester_2
    TEST_MODE = Automatic
    TEST_CLAUSE:
      TEST @Value(GNR) = $(gnr)
      TEST @Value(BNR) = $(bnr)
    BOOL_OP = AND
    TEST_DESCRIPTION = ""
    PASSED -> HTTPCaller
    PASSED -> Tester_2_Passed
    FAILED -> Counter_2
Counter_2
    CNT_ATTR = _count_next
    DOMAIN = counter
    START = 0
    SCOPE = Local
    -> Tester
Tester
    TEST_MODE = Automatic
    TEST_CLAUSE = TEST @Value(_count_next) = @Value(_max)
    BOOL_OP = OR
    TEST_DESCRIPTION = ""
    PASSED -> Terminator
Terminator
    MESSAGE = Translation Terminated
Tester_2_Passed: Inspector
HTTPCaller
    OUTPUT_DIRNAME = $(FME_MF_DIR)Ferdigattest_fra_ePhorte
    FILE_PATH_ATTR = filecopy_source_dataset
    HTTP_METHOD = GET
    SAVE_FILE = File
    SAVE_MULTI = Yes
    AUTH_USERNAME = paaped
    TARGET_URL = @Value(LINK_dok1)
    RESPONSE_HEADER_LIST_ATTR = _headers
    FOLLOW_REDIRECTS = Yes
    AUTH_PASSWORD = $(PASSWORD)
    TRANSFER_TIMEOUT_LENGTH = 90
    CONNECTION_TIMEOUT_LENGTH = 60
    STATUS_CODE_ATTR = _http_status_code
    ERROR_ATTR = _error
    USE_COOKIES = Yes
    VERIFY_SSL_CERTIFICATES = Yes
    AUTH_METHOD = NTLM
    -> ParameterFetcher
ParameterFetcher
    ATTR_LIST = _Ordrenavn {$(Ordrenavn)}
    -> AttributeFilter
AttributeFilter
    ATTR_NAME = VE_DOKFORMAT_LF
    ATTR_VALUES = RA-PDF,DOC,DOCS,WORD,<EMPTY>,<MISSING>,<NULL>,<UNFILTERED>
    RA-PDF -> ListBuilder
    DOC -> ListBuilder_2
    DOCS -> ListBuilder_2
    WORD -> ListBuilder_2
ListBuilder
    LIST_NAME = _list
    GRP_BY = _Ordrenavn
    -> ListExploder
ListExploder
    ATTR_CONFLICT_RES = Use Incoming List
    INDEX_ATTR = _element_index
    ATTR_ACCUM_MODE = Merge Incoming List
    LIST_ATTR = _list{}
    ELEMENTS -> AttributeCreator
AttributeCreator
    ATTR_TABLE:
      SET_TO filecopy_dest_filename = @Value(_Ordrenavn)_@Value(_element_index).pdf
      SET_TO filecopy_dest_dataset = $(FME_MF_DIR_ENCODED)ftp\upload
    -> filecopy (writer FILECOPY_1)
ListBuilder_2
    LIST_NAME = _list
    GRP_BY = _Ordrenavn
    -> ListExploder_2
ListExploder_2
    ATTR_CONFLICT_RES = Use Incoming List
    INDEX_ATTR = _element_index
    ATTR_ACCUM_MODE = Merge Incoming List
    LIST_ATTR = _list{}
    ELEMENTS -> AttributeCreator_2
AttributeCreator_2
    ATTR_TABLE:
      SET_TO filecopy_dest_filename = @Value(_Ordrenavn)_@Value(_element_index).doc
      SET_TO filecopy_dest_dataset = $(FME_MF_DIR_ENCODED)ftp\upload
    -> filecopy (writer FILECOPY_1)
filecopy (writer FILECOPY_1)
StringSearcher
    CASE = no
    REGEXP = \d+[,]\d+
    MATCHED_RESULT_ATTR = _first_match
    STRING_TO_SEARCH = @Value(JP_INNHOLD_G)

FME custom transformer Ferdigattest

Parameters:
- JP_INNHOLD_G_2 = @Value(JP_INNHOLD_G)   # Jp Innhold G

Input (input)
    -> StringCaseChanger
StringCaseChanger
    ATTRLIST = JP_INNHOLD_G
    ATTRCHOICE = Selected Attributes
    CHANGE_TYPE = lowercase
    -> Tester_2
Tester_2
    TEST_MODE = Automatic
    TEST_CLAUSE:
      TEST @Value(JP_INNHOLD_G) NOT_CONTAINS søknad
      TEST @Value(JP_INNHOLD_G) NOT_CONTAINS anmodning
      TEST @Value(JP_INNHOLD_G) NOT_CONTAINS avslag
      TEST @Value(JP_INNHOLD_G) NOT_CONTAINS forespørsel
      TEST @Value(JP_INNHOLD_G) NOT_CONTAINS vedrørende
      TEST @Value(JP_INNHOLD_G) NOT_CONTAINS manglende
      TEST @Value(JP_INNHOLD_G) NOT_CONTAINS salg
      TEST @Value(JP_INNHOLD_G) NOT_CONTAINS megler
      TEST @Value(JP_INNHOLD_G) NOT_CONTAINS opplysninger
      TEST @Value(JP_INNHOLD_G) NOT_CONTAINS beboelse
      TEST @Value(JP_INNHOLD_G) NOT_CONTAINS uten
      TEST @Value(JP_INNHOLD_G) NOT_CONTAINS etterlyser
    BOOL_OP = AND
    TEST_DESCRIPTION = ""
    PASSED -> Ferdigattest (output)
Ferdigattest (output)
