FME workspace Flyfoto_3.fmw

Parameters:
- DestDataset_PDF2D = $(FME_MF_DIR)ftp\upload   # Destination PDF File
- _gnr =   # Gnr
- _bnr =   # Bnr
- _fnr =   # Fnr
- _snr =   # Snr
- A4 = YES   # A4 proportion
- DestDataset_SQLITE3 = X:\Data\SQLITE\0229_UTVALG_EIENDOM.sl3   # Destination SQLite Database File

Writers:
- PDF2D_1: PDF2D to $(DestDataset_PDF2D)

Creator
    NUM = 1
    GEOMTYPE = Geometry Object
    CREATED -> ParameterFetcher
ParameterFetcher
    ATTR_LIST = GNR {$(_gnr)} BNR {$(_bnr)} FNR {$(_fnr)} SNR {$(_snr)}
    -> WorkspaceRunner
WorkspaceRunner
    WORKSPACE_FILE = $(FME_MF_DIR)UTVALG_EIENDOM.fmw
    WORKSPACE_PARAMETERS = GNR,$(_gnr),BNR,$(_bnr),FNR,$(_fnr),SNR,$(_snr),DestDataset_SQLITE3,$(DestDataset_SQLITE3)
    BLOCKING = Yes
    SUCCEEDED -> FeatureReader [INITIATOR]
    FAILED -> WorkspaceRunner_2
WorkspaceRunner_2
    WORKSPACE_FILE = $(FME_MF_DIR)UTVALG_EIENDOM.fmw
    WORKSPACE_PARAMETERS = GNR,$(_gnr),BNR,$(_bnr),FNR,$(_fnr),SNR,0,DestDataset_SQLITE3,$(DestDataset_SQLITE3)
    BLOCKING = Yes
    SUCCEEDED -> FeatureReader [INITIATOR]
FeatureReader
    INTERACT = <No Spatial Filter>
    ATTR_ACCUM_MODE = Only Use Result
    DATASET = $(DestDataset_SQLITE3)
    FEATURETYPES = Teig
    COMBINE_GEOM = Use Result
    SPATIALITE_QUERY_FEATURE_TYPES_FOR_MERGE_FILTERS = Yes
    OUTPUT_FEATURES_DISPLAY = Schema and Data Features
    FORMAT = SPATIALITE
    ATTRIBUTES = Teig,"PRIMARYINDEX,BEREGNETAREAL_AREAL,BEREGNETAREAL_AREALMERKNAD,BEREGNETAREAL_AREALMERKNAD{}_AREALMERKNAD,AREALKILDE,HOVEDTEIG,MATRID_MATRIKKELENHET,MATRIKKELENHETSTYPE,BNR,FNR,GNR,SNR,TINGLYST,TEIG-ID,TEIGMEDFLEREMATRENHETER"
    Teig -> BoundingBoxReplacer_2
    Teig -> MerkEiendom
MerkEiendom
    _gnr = $(_gnr)
    _bnr = $(_bnr)
    _fnr = $(_fnr)
    _snr = $(_snr)
    label -> MapnikRasterizer [Label00]
    Line -> MapnikRasterizer [Teig]
    Polygon -> MapnikRasterizer [Teig00]
BoundingBoxReplacer_2
    BOXTYPE = Bounding Box
    BOX -> Tester
Tester
    TEST_CLAUSE = TEST @Area() < 50000
    BOOL_OP = OR
    TEST_DESCRIPTION = ""
    TEST_MODE = Automatic
    PASSED -> WMS_3
    FAILED -> Terminator
WMS_3
    WMS_layer = GNRBNR_ORTO,ADRESSE_ORTO,PBLTILTAK_ORTO,EIENDOMSKART,FLYFOTO14
    ratio_l = 271.75
    WMS_url = http://195.1.20.83/wms-follo
    A4 = YES
    ratio_s = 210.0
    -> Ramme [BoundingBoxAccumulator_Input]
    -> MeasureLineCreator
    -> Bounding
    -> MapnikRasterizer [Output]
    -> TextRepalcer
Note: TextRepalcer [TextRepalcer] / [Embedded] / BNR: @Value(BNR) / FNR: @Value(FNR) / GNR: @Value(GNR) / SNR: @Value(SNR)
TextRepalcer
    SNR = @Value(SNR)
    GNR = @Value(GNR)
    FNR = @Value(FNR)
    BNR = @Value(BNR)
    Output_2 -> MapnikRasterizer [Output_2]
    Dato -> MapnikRasterizer [Output_3]
MeasureLineCreator
    Line -> MapnikRasterizer [Line]
    Label -> MapnikRasterizer [Label]
Bounding
    Higth = 24
    -> MapnikRasterizer [Top_layout]
    -> Ramme [BoundingBoxAccumulator_Input]
Ramme
    BoundsExtractor_Output -> MapnikRasterizer [Coerced]
    BoundsExtractor_Output -> BoundingBoxReplacer
MapnikRasterizer
    BACKGROUND_COLOR = 1,1,1
    GROUND_EXTENTS_MAX_Y = @Value(ymax)
    COLROW_OR_SPACING = Spacing
    LAYER_CARDINALITY = Each rendering rule is a layer
    INTERPRETATION_TYPE = RGBA32
    GROUND_EXTENTS_MIN_Y = @Value(xmax)
    GROUND_EXTENTS_MIN_X = @Value(xmin)
    MAPNIK_CONFIG = Top_layout;raster;__ignore__raster-properties-group;;opacity;1;scaling;near;__ignore__comp-group;;comp-op;src-over;Output;raster;__ignore__raster-properties-group;;opacity;1;scaling;near;__ignore__comp-group;;comp-op;src-over;Output_2;text;__ignore__text-properties-group;;name;gnavn;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Output_3;text;__ignore__text-properties-group;;name;_timestamp;face-name;Tahoma,Normal;size;@Value(text_hight);__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;right;justify-alignment;left;vertical-alignment;top;__ignore__comp-group;;comp-op;src-over;Coerced;line;__ignore__color-group;;stroke;0,0,0;stroke-opacity;1;__ignore__line-style-group;;stroke-width;9;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Line;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over;Teig00;polygon;__ignore__color-group;;fill;1,0.607843,0.607843;fill-opacity;0.3;__ignore__smoothing-group;FME_DISCLOSURE_OPEN;gamma;1;gamma-method;linear;smooth;0;__ignore__comp-group;FME_DISCLOSURE_OPEN;comp-op;src-over;Teig;line;__ignore__color-group;;stroke;1,0,0;stroke-opacity;1;__ignore__line-style-group;;stroke-width;3;stroke-linejoin;miter;stroke-linecap;butt;stroke-dasharray;"12 6";stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;Label00;text;__ignore__text-properties-group;;name;salgsobjekt;face-name;Tahoma,Normal;size;10;__ignore__color-group;;fill;1,0,0;opacity;1;halo-fill;1,1,1;halo-radius;0;__ignore__positioning-group;;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;;comp-op;src-over;Label;text;__ignore__text-properties-group;;name;label;face-name;Tahoma,Normal;size;@Evaluate(4*@Value(dy));__ignore__color-group;;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;middle;justify-alignment;center;vertical-alignment;top;__ignore__comp-group;;comp-op;src-over
    SPECIFY_GROUND_EXTENTS = Specify ground extents
    BACKGROUND_COLOR_ALPHA = 1.0
    SPACING = 0.1
    GROUND_EXTENTS_MAX_X = @Value(ymin)
    RASTER -> Clipper [CLIPPEE]
BoundingBoxReplacer
    BOXTYPE = Bounding Box
    BOX -> Clipper [CLIPPER]
Clipper
    PRESERVE_CLIPPEE_EXTENTS = No
    CREATE_AGGREGATES = Yes
    CLIP_TYPE = Multiple Clippers
    BOUNDARY_CASES = Treat as Inside
    CLIPPED_ATTR = _clipped
    LINES_AS_SEGMENTS = No
    CONNECT_Z_MODE = First Wins
    INSIDE -> PDFPageFormatter [Inside]
PDFPageFormatter
    PAGE_UNITS = Centimeters
    PAGE_NUMBER = 1
    PAGE_HEIGHT_PTS = 842
    PAGE_ORIENTATION = Portrait
    PAGE_SIZE = A4
    PAGE_HEIGHT_USER = 29.7
    PAGE_OBJECTS = "Inside WIDTH;566.93;FIXED_ASPECT;Yes;SIZE_PARAMS;;MINY;14.29;MINX;14.17;HEIGHT;813.54;CLIPPING_ENABLED;No;SCALING_PARAMS;"
    PAGE_WIDTH_PTS = 595
    PAGE_WIDTH_USER = 21
    -> Teig (writer PDF2D_1)
Teig (writer PDF2D_1)
Terminator
    MESSAGE = Translation Terminated

FME custom transformer Bounding

Parameters:
- Higth =   # Hight Frame

Input (input)
    -> BoundsExtractor
BoundsExtractor
    ZMAX = _zmax
    XMAX = _xmax
    XMIN = _xmin
    ZMIN = _zmin
    YMIN = _ymin
    YMAX = _ymax
    -> ParameterFetcher
ParameterFetcher
    ATTR_LIST = _Higth {$(Higth)}
    -> PythonCaller
PythonCaller
    PYTHONSOURCE:
      import fme
      import fmeobjects
      # Template Function interface:
      def processFeature(feature):
          pass

      # Template Class Interface:
      class FeatureProcessor(object):
          def __init__(self):
              self.y0=0
              self.y1=0
          def input(self,feature):
              self.y0 = float(feature.getAttribute('_ymax'))
              self.y  = float(feature.getAttribute('_ymin'))
              self.dy=self.y0 - self.y

              self.y1=self.y0+float(feature.getAttribute('_Higth'))*self.dy/252.0

              feature.setAttribute('_ymin',self.y0)
              feature.setAttribute('_ymax',self.y1)
              self.pyoutput(feature)
          def close(self):
              del self
    NEW_ATTRIBUTES = _ymin _ymax
    PYTHONSYMBOL = FeatureProcessor
    -> VertexCreator
VertexCreator
    MODE_NAME = Replace with Point
    XVAL = @Value(_xmin)
    YVAL = @Value(_ymin)
    -> VertexCreator_4
VertexCreator_4
    MODE_NAME = Add Point
    XVAL = @Value(_xmax)
    YVAL = @Value(_ymax)
    -> BoundsExtractor_2
BoundsExtractor_2
    ZMAX = _zmax
    XMAX = _xmax
    XMIN = _xmin
    ZMIN = _zmin
    YMIN = _ymin
    YMAX = _ymax
    -> FeatureReader [INITIATOR]
FeatureReader
    INTERACT = <No Spatial Filter>
    ATTR_ACCUM_MODE = Only Use Result
    DATASET = $(FME_MF_DIR_ENCODED)Layout\Meglerkart-Flyfotografi.JPG
    JPEG_USE_SEARCH_ENVELOPE = NO
    JPEG_CLIP_TO_ENVELOPE = NO
    COMBINE_GEOM = Use Result
    JPEG_APPLY_GCPS = No
    OUTPUT_FEATURES_DISPLAY = Schema and Data Features
    FORMAT = JPEG
    JPEG_GROUP_BY_DATASET = No
    ATTRIBUTES = JPEG,exif_artist
    JPEG -> Counter_2
    INITIATOR -> Counter
Counter_2
    SCOPE = Local
    DOMAIN = id
    START = 0
    CNT_ATTR = id
    -> FeatureMerger [REQUESTOR]
Counter
    SCOPE = Local
    DOMAIN = id
    START = 0
    CNT_ATTR = id
    -> FeatureMerger [SUPPLIER]
FeatureMerger
    MERGE_TYPE = Attributes Only
    ATTR_CONFLICT_RES = Use Requestor
    IGNORE_NULLS = No
    REJECT_NULL_MISSING_KEYS = No
    ATTR_ACCUM_MODE = Merge Supplier
    PROCESS_DUPS = No
    JOIN_KEYS = @Value(id) @Value(id) AUTO
    SUPPLIERS_FIRST = No
    MERGED -> RasterGeoreferencer
RasterGeoreferencer
    X_LL_COORD = @Value(_xmin)
    X_LR_COORD = @Value(_xmax)
    Y_LL_COORD = @Value(_ymin)
    POINTANDANGLE_OR_EXTENTS = Extents
    X_UL_COORD = @Value(_xmin)
    Y_UR_COORD = @Value(_ymax)
    Y_UL_COORD = @Value(_ymax)
    X_UR_COORD = @Value(_xmax)
    Y_LR_COORD = @Value(_ymin)
    -> AttributeRemover
AttributeRemover
    REMOVE_ATTRS = _zmin,_ymin,_zmax,_xmax,pdf_page_number,_xmin,_ymax
    -> Output (output)
Output (output)

FME custom transformer WMS_3

Parameters:
- WMS_url =
- WMS_layer =
- Username =   # Enter Username
- password =   # Enter password
- A4 = NO   # A4 proportion
- ratio_l = 229.75   # Length of long side
- ratio_s = 210.0   # Length of shorter side

Input (input)
    -> BoundsExtractor
BoundsExtractor
    XMAX = _hmax
    XMIN = _hmin
    YMIN = _vmin
    YMAX = _vmax
    -> Tester
Tester
    TEST_CLAUSE = TEST $(A4) = NO
    BOOL_OP = OR
    TEST_DESCRIPTION = ""
    TEST_MODE = Automatic
    PASSED -> AttributeCreator
    FAILED -> ParameterFetcher
ParameterFetcher
    ATTR_LIST = _ratio_l {$(ratio_l)} _ratio_s {$(ratio_s)}
    -> AttributeCreator_4
AttributeCreator_4
    ATTR_TABLE:
      SET_TO _ratio_l = @real64(@Value(_ratio_l))
      SET_TO _ratio_s = @real64(@Value(_ratio_s))
    -> PythonCaller
PythonCaller
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self.hmax=feature.getAttribute('_hmax')
              self.hmin=feature.getAttribute('_hmin')
              self.vmax=feature.getAttribute('_vmax')
              self.vmin=feature.getAttribute('_vmin')

              self.dh=self.hmax-self.hmin
              self.dv=self.vmax-self.vmin

              self.hmean = (self.hmax + self.hmin)/2.0
              self.vmean = (self.vmax + self.vmin)/2.0

              if self.dv < feature.getAttribute('_ratio_l') and self.dh < feature.getAttribute('_ratio_s'):
                  self.vmin= self.vmean-feature.getAttribute('_ratio_l')/2.0
                  self.vmax= self.vmean+feature.getAttribute('_ratio_l')/2.0
                  self.hmin = self.hmean-feature.getAttribute('_ratio_s')/2.0
                  self.hmax = self.hmean+feature.getAttribute('_ratio_s')/2.0
              elif self.dh > self.dv and self.dv > feature.getAttribute('_ratio_l'):
                  self.ndv = self.dh*(feature.getAttribute('_ratio_l')/feature.getAttribute('_ratio_s'))
                  self.vmin= self.vmean-self.ndv/2.0
                  self.vmax= self.vmean+self.ndv/2.0
              elif self.dh < self.dv and self.dh > feature.getAttribute('_ratio_s'):
                  self.ndh  = self.dv*(feature.getAttribute('_ratio_s')/feature.getAttribute('_ratio_l'))
                  self.hmin = self.hmean-self.ndh/2.0
                  self.hmax = self.hmean+self.ndh/2.0
              else:
                  raise Exception('condition not met')
                  print 'condition not met'


              #self.dh=self.hmax-self.hmin
              #self.dv=self.vmax-self.vmin

              #print self.dh, self.dv

              feature.setAttribute('_hmax',self.hmax)
              feature.setAttribute('_hmin',self.hmin)
              feature.setAttribute('_vmax',self.vmax)
              feature.setAttribute('_vmin',self.vmin)
              self.pyoutput(feature)
          def close(self):
              pass
    PYTHONSYMBOL = FeatureProcessor
    -> VertexCreator
VertexCreator
    MODE_NAME = Replace with Point
    XVAL = @Value(_hmin)
    YVAL = @Value(_vmin)
    -> VertexCreator_2
VertexCreator_2
    MODE_NAME = Add Point
    XVAL = @Value(_hmax)
    YVAL = @Value(_vmax)
    -> BoundingBoxReplacer
BoundingBoxReplacer
    BOXTYPE = Bounding Box
    BOX -> AttributeCreator
AttributeCreator
    ATTR_TABLE:
      SET_TO h_t = @Evaluate(@round((@Value(_hmax)-@Value(_hmin))/200)+1)
      SET_TO v_t = @Evaluate(@round((@Value(_vmax)-@Value(_vmin))/200)+1)
      SET_TO dh = @Evaluate(@Value(_hmax)-@Value(_hmin))
      SET_TO dv = @Evaluate(@Value(_vmax)-@Value(_vmin))
    -> Tester_2
Tester_2
    TEST_CLAUSE:
      TEST @Value(dv) > 1000
      TEST @Value(dh) > 1000
    BOOL_OP = OR
    TEST_DESCRIPTION = ""
    TEST_MODE = Automatic
    PASSED -> Tiler
    FAILED -> AttributeRemover_3
Tiler
    YINC = 1000
    XINC = 1000
    ROW_ATTR = _row
    BOUNDARY_CASES = No
    COL_ATTR = _column
    TILING_TYPE = Tile Size
    TILED -> AttributeRemover
AttributeRemover
    REMOVE_ATTRS = _vmax,_vmin,_column,h_t,_hmax,_hmin,v_t,_row
    -> BoundsExtractor_2
BoundsExtractor_2
    XMAX = _xmax
    XMIN = _xmin
    YMIN = _ymin
    YMAX = _ymax
    -> AttributeRounder
AttributeRounder
    PLACES = 0
    SRC_ATTRS = _xmax _ymax
    ROUND_TYPE = Up
    -> AttributeRounder_2
AttributeRounder_2
    PLACES = 0
    SRC_ATTRS = _xmin _ymin
    ROUND_TYPE = Down
    -> AttributeCreator_2
AttributeCreator_2
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*3)&HEIGHT=@Evaluate((@Value(_ymax)-@Value(_ymin))*3)&SRS=EPSG:25832&TRANSPARENT=true&BBOX=@Value(_xmin),@Value(_ymin),@Value(_xmax),@Value(_ymax)&
    -> HTTPCaller_3
HTTPCaller_3
    AUTH_PASSWORD = $(password)
    FOLLOW_REDIRECTS = Yes
    CONNECTION_TIMEOUT_LENGTH = 60
    RESPONSE_HEADER_LIST_ATTR = _headers
    TRANSFER_TIMEOUT_LENGTH = 90
    AUTH_USERNAME = $(Username)
    TARGET_ATTR_ENCODING = auto-detect
    SAVE_FILE = Attribute
    ERROR_ATTR = _error
    TARGET_URL = @Value(_wms2)
    STATUS_CODE_ATTR = _http_status_code
    VERIFY_SSL_CERTIFICATES = Yes
    USE_COOKIES = No
    HTTP_METHOD = GET
    AUTH_METHOD = Basic
    TARGET_ATTR = _response_body
    -> RasterReplacer_2
AttributeRemover_3
    REMOVE_ATTRS = _hmin,_vmax,_vmin,dv,v_t,dh,_hmax,h_t
    -> BoundsExtractor_3
BoundsExtractor_3
    XMAX = _xmax
    XMIN = _xmin
    YMIN = _ymin
    YMAX = _ymax
    -> AttributeRounder_3
AttributeRounder_3
    PLACES = 0
    SRC_ATTRS = _xmax _ymax
    ROUND_TYPE = Up
    -> AttributeRounder_4
AttributeRounder_4
    PLACES = 0
    SRC_ATTRS = _xmin _ymin
    ROUND_TYPE = Down
    -> AttributeCreator_3
AttributeCreator_3
    ATTR_TABLE:
      SET_TO _wms = $(WMS_url)?VERSION=1.1.1&REQUEST=GetMap&SERVICE=WMS&LAYERS=$(WMS_layer)&FORMAT=image/png&WIDTH=@Evaluate((@Value(_xmax)-@Value(_xmin))*10)&HEIGHT=@Evaluate((@Value(_ymax)-@Value(_ymin))*10)&SRS=EPSG:25832&TRANSPARENT=true&BBOX=@Value(_xmin),@Value(_ymin),@Value(_xmax),@Value(_ymax)&
      SET_TO _wms2 = $(WMS_url)?VERSION=1.1.1&REQUEST=GetMap&SERVICE=WMS&LAYERS=$(WMS_layer)&FORMAT=image/png&WIDTH=@Evaluate((@Value(_xmax)-@Value(_xmin))*4)&HEIGHT=@Evaluate((@Value(_ymax)-@Value(_ymin))*4)&SRS=EPSG:25832&TRANSPARENT=true&BBOX=@Value(_xmin),@Value(_ymin),@Value(_xmax),@Value(_ymax)&
    -> HTTPCaller_2
HTTPCaller_2
    AUTH_PASSWORD = $(password)
    FOLLOW_REDIRECTS = Yes
    CONNECTION_TIMEOUT_LENGTH = 60
    RESPONSE_HEADER_LIST_ATTR = _headers
    TRANSFER_TIMEOUT_LENGTH = 90
    AUTH_USERNAME = $(Username)
    TARGET_ATTR_ENCODING = auto-detect
    SAVE_FILE = Attribute
    ERROR_ATTR = _error
    TARGET_URL = @Value(_wms)
    STATUS_CODE_ATTR = _http_status_code
    VERIFY_SSL_CERTIFICATES = Yes
    USE_COOKIES = No
    HTTP_METHOD = GET
    AUTH_METHOD = Basic
    TARGET_ATTR = _response_body
    -> RasterReplacer_2
RasterReplacer_2
    BLOB_ATTR = _response_body
    FORMAT = PNGRASTER
    REMOVE_ATTRIBUTE = No
    -> RasterCheckpointer
RasterCheckpointer
    -> RasterGeoreferencer_2
RasterGeoreferencer_2
    X_LL_COORD = @Value(_xmin)
    X_LR_COORD = @Value(_xmax)
    Y_LL_COORD = @Value(_ymin)
    POINTANDANGLE_OR_EXTENTS = Extents
    X_UL_COORD = @Value(_xmin)
    Y_UR_COORD = @Value(_ymax)
    Y_UL_COORD = @Value(_ymax)
    X_UR_COORD = @Value(_xmax)
    Y_LR_COORD = @Value(_ymin)
    -> AttributeRemover_2
AttributeRemover_2
    LIST_ATTRS = _headers{} _headers{}.name _headers{}.value
    REMOVE_ATTRS = _ymax,_xmax,_ymin,_wms,_wms2,dv,_http_status_code,_xmin,dh,_response_body
    -> RasterCheckpointer_2
RasterCheckpointer_2
    -> RasterMosaicker
RasterMosaicker
    MERGE_PALETTES_NAME = Yes
    COMPOSITE_USING_ALPHA_BAND_NAME = No
    SNAPPING_TYPE_NAME = Resample
    INTERPOLATION_TYPE_NAME = Nearest Neighbor
    ACCUM_ATTRS_NAME = Get Attributes From One Representative Feature
    NODATA_OVERWRITE = No
    -> Output (output)
Output (output)

FME custom transformer Ramme

BoundingBoxAccumulator_Input (input)
    -> BoundingBoxAccumulator
BoundingBoxAccumulator
    ACCUM_ATTRS_NAME = Get Attributes From One Representative Feature
    TOPFER_INDEX = No
    BOUNDING_BOX -> GeometryCoercer
GeometryCoercer
    KIND = fme_line
    GQUERY:
      for $geom in //geometry
      where $geom/count(parent::geometry) = 0
      return number($geom/@fme_id)
    COERCED -> BoundsExtractor
BoundsExtractor
    XMAX = xmax
    XMIN = xmin
    YMIN = ymin
    YMAX = ymax
    -> BoundsExtractor_Output (output)
BoundsExtractor_Output (output)

FME custom transformer MerkEiendom

Parameters:
- _gnr = 115   # Gnr
- _bnr = 312   # Bnr
- _fnr = 0   # Fnr
- _snr = 0   # Snr

Input (input)
    -> DonutHoleExtractor
    -> Polygon (output)
DonutHoleExtractor
    OUTERSHELL -> GeometryCoercer
    HOLE -> GeometryCoercer
GeometryCoercer
    KIND = fme_line
    GQUERY:
      for $geom in //geometry
      where $geom/count(parent::geometry) = 0
      return number($geom/@fme_id)
    COERCED -> AttributeCreator
    COERCED -> Line (output)
AttributeCreator
    ATTR_TABLE = SET_TO salgsobjekt = Salgs objekt!
    -> Chopper
Chopper
    GRID_AREAS = Yes
    APPROX_LENGTH = 50
    CHOPPED_ATTR = _chopped
    MODE = By Length
    -> OrientationExtractor
OrientationExtractor
    ORIENTATION = _orientation
    -> LabelPointReplacer
LabelPointReplacer
    LABATTR = @Value(salgsobjekt)
    HEIGHT = 20
    ALWAYSROTATE = no
    LabelPoint -> label (output)
label (output)
Line (output)
Polygon (output)

FME custom transformer TextRepalcer
Adds a number layer on each side.

Parameters:
- BNR = @Value(BNR)
- FNR = @Value(FNR)
- GNR = @Value(GNR)
- SNR = @Value(SNR)

Input (input)
    -> BoundingBoxReplacer
BoundingBoxReplacer
    BOXTYPE = Bounding Box
    BOX -> BoundsExtractor
BoundsExtractor
    ZMAX = _zmax
    XMAX = _xmax
    XMIN = _xmin
    ZMIN = _zmin
    YMIN = _ymin
    YMAX = _ymax
    -> PythonCaller_2
PythonCaller_2
    PYTHONSOURCE:
      import fme
      import fmeobjects
      # Template Function interface:
      def processFeature(feature):
          pass

      # Template Class Interface:
      class FeatureProcessor(object):
          def __init__(self):
              pass
          def input(self,feature):
              self.y0=feature.getAttribute('_ymax')
              self.y=feature.getAttribute('_ymin')

              self.y1=self.y0+9*(self.y0-self.y)/252
              self.y2=self.y0+3*(self.y0-self.y)/252
              self.hight=30*(self.y0-self.y)/252

              self.x=feature.getAttribute('_xmax')
              self.x0=feature.getAttribute('_xmin')

              self.x1=self.x0+39*(self.x-self.x0)/190
              self.x2=self.x0+39*(self.x-self.x0)/190 #tidligere + 97


              feature.setAttribute('_xmin',self.x1)
              feature.setAttribute('_ymax',self.y1)
              feature.setAttribute('_ymin',self.y2)
              feature.setAttribute('_xmax',self.x2)
              feature.setAttribute('text_hight',self.hight)

              self.pyoutput(feature)
          def close(self):
              del self
    NEW_ATTRIBUTES = _xmin _ymax _xmax _ymin text_hight
    PYTHONSYMBOL = FeatureProcessor
    -> VertexCreator_2
    -> VertexCreator_4
VertexCreator_2
    MODE_NAME = Replace with Point
    XVAL = @Value(_xmin)
    INDEX = 0
    YVAL = @Value(_ymax)
    -> StringFormatter
StringFormatter
    SRC_ATTRS = GNR,BNR,SNR,FNR
    FORMAT = 4s
    -> AttributeCreator
AttributeCreator
    ATTR_LIST = gnavn,GNR: @Value(GNR) BNR: @Value(BNR) FNR: @Value(FNR) SNR: @Value(SNR)
    -> LabelPointReplacer_2
LabelPointReplacer_2
    LABATTR = @Value(gnavn)
    HEIGHT = @Value(text_hight)
    ALWAYSROTATE = yes
    LabelPoint -> Output_2 (output)
Output_2 (output)
VertexCreator_4
    MODE_NAME = Replace with Point
    XVAL = @Value(_xmax)
    INDEX = 0
    YVAL = @Value(_ymin)
    -> TimeStamper
TimeStamper
    FMT = ^d.^m.^Y
    TIME_ATTR = _timestamp
    -> AttributeCreator_2
AttributeCreator_2
    ATTR_TABLE = SET_TO _timestamp = Dato: @Value(_timestamp)        Enebakk Kommune
    -> LabelPointReplacer_3
LabelPointReplacer_3
    LABATTR = @Value(_timestamp)
    HEIGHT = @Value(text_hight)
    ALWAYSROTATE = yes
    LabelPoint -> Dato (output)
Dato (output)

FME custom transformer MeasureLineCreator

Input (input)
    -> BoundsExtractor
BoundsExtractor
    XMAX = _xmax
    XMIN = _xmin
    YMIN = _ymin
    YMAX = _ymax
    -> AttributeCreator
AttributeCreator
    ATTR_TABLE:
      SET_TO size = @ceil(@Evaluate(@Value(_xmax)-@Value(_xmin))/5)
      SET_TO dy = @floor(@Evaluate((@Value(_ymax)-@Value(_ymin))/15))
      SET_TO dx = @floor(@Evaluate((@Value(_ymax)-@Value(_ymin))/15))
    -> TestFilter
TestFilter
    DEFAULT_VALUE = <UNFILTERED>
    TEST_LIST:
      BOOL_OP,AND,COMPOSITE_TEST,<Unused>,TEST_CLAUSE,"TEST @Value(size) >= 0
      TEST @Value(size) < 100",< 100,BOOL_OP,AND,COMPOSITE_TEST,<Unused>,TEST_CLAUSE,"TEST @Value(size) >= 100
      TEST @Value(size) < 1000",< 1000,BOOL_OP,AND,COMPOSITE_TEST,<Unused>,TEST_CLAUSE,"TEST @Value(size) >= 1000
      TEST @Value(size) < 10000",< 10000,BOOL_OP,AND,COMPOSITE_TEST,<Unused>,TEST_CLAUSE,"TEST @Value(size) >= 10000
      TEST @Value(size) < 100000",< 100000
    < 100 -> AttributeRounder
    < 1000 -> AttributeRounder_2
    < 10000 -> AttributeRounder_3
    < 100000 -> AttributeRounder_4
AttributeRounder
    PLACES = -1
    SRC_ATTRS = size
    ROUND_TYPE = Nearest
    -> VertexCreator
AttributeRounder_2
    PLACES = -2
    SRC_ATTRS = size
    ROUND_TYPE = Nearest
    -> VertexCreator
VertexCreator
    MODE_NAME = Replace with Point
    XVAL = @Evaluate(@Value(_xmax)-@Value(dx))
    YVAL = @Evaluate(@Value(_ymin)+@Value(dy))
    -> VertexCreator_2
    -> VertexCreator_5
VertexCreator_5
    MODE_NAME = Add Point
    XVAL = @Evaluate(@Value(_xmax)-@Value(dx))
    YVAL = @Evaluate(@Value(_ymin)+2*@Value(dy))
    -> Line (output)
VertexCreator_2
    MODE_NAME = Add Point
    XVAL = @Evaluate(@Value(_xmax)-@Value(dx)-@Value(size))
    YVAL = @Evaluate(@Value(_ymin)+@Value(dy))
    -> AttributeCreator_2
    -> VertexCreator_6
VertexCreator_6
    MODE_NAME = Add Point
    XVAL = @Evaluate(@Value(_xmax)-@Value(dx)-@Value(size))
    YVAL = @Evaluate(@Value(_ymin)+2*@Value(dy))
    -> Line (output)
AttributeCreator_2
    ATTR_TABLE = SET_TO BENEVNING = m
    -> Line (output)
    -> AttributeCreator_4
Line (output)
AttributeRounder_3
    PLACES = -3
    SRC_ATTRS = size
    ROUND_TYPE = Nearest
    -> VertexCreator_3
AttributeRounder_4
    PLACES = -4
    SRC_ATTRS = size
    ROUND_TYPE = Nearest
    -> VertexCreator_3
VertexCreator_3
    MODE_NAME = Replace with Point
    XVAL = @Evaluate(@Value(_xmax)-@Value(dx))
    YVAL = @Evaluate(@Value(_ymin)+@Value(dy))
    -> VertexCreator_4
VertexCreator_4
    MODE_NAME = Add Point
    XVAL = @Evaluate(@Value(_xmax)-@Value(dx)-@Value(size))
    YVAL = @Evaluate(@Value(_ymin)+@Value(dy))
    -> AttributeCreator_3
AttributeCreator_3
    ATTR_TABLE:
      SET_TO BENEVNING = Km
      SET_TO size = @Evaluate(@Value(size)/1000)
    -> AttributeCreator_4
AttributeCreator_4
    ATTR_TABLE = SET_TO label = @int(@Value(size))@Value(BENEVNING)
    -> LabelPointReplacer
LabelPointReplacer
    LABATTR = @Value(label)
    HEIGHT = @Evaluate(2*@Value(dy))
    ALWAYSROTATE = yes
    LabelPoint -> Label (output)
Label (output)
